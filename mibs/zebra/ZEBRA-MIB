--(C) Copyright 2023, Zebra Technologies Corp.

--
--9   - Link-OS 6.x Updates (zbrTrackedAlertsCode,zbrOptUnsAlertsCondition,...) additions (zbrEzplTakeLabelCalibration,zbrMediaLinerlessOffset,zbrCutter,...)
--8   - Link-OS 6.8 wireless security settings,
--7   - Link-OS 6.7 Updates mqtt, additions generateStatusAlerts
--6   - Link-OS 6.5 Update zbrWLanSecurUserName length, additions (zbrBluetoothDisconnectIdleLink, zbrBluetoothSniffModeEnable, zbrControlReprint)
--5   - Link-OS 6.4 additions (zbrPrintXiCompatibilityAdjust)
--4   - Link-OS 6.3 Updates zbrTrackedAlertsTable to include alert clearing, additions (zbrDeviceResetButtonEnable, zbrWLanSetupDhcpRequired, zbrAplSettings, ...)
--    - Link-OS 6.2 additions (zbrOdometerNetRibbonUse, zbrOdometerNetMediaUse, zbrTrackedAlertsTable, zbrSuppliesMediaCartTable, zbrSuppliesRibbonCartTable, ...)
--    - Link-OS 4,5 additions (LinkOSConnector,TLS, HTTPS, Firewall,platform features,..) removal (zbrTcpSecurityTable, zbrTcpMLPTable) 
--    - LINK-OS 3.0 additions (Ntp, ...)
--    - LINK-OS     additions (Weblink, CaptureData, ..)
--3   - Expanding coverage (wireless, bluetooth, serial, ...)
--1.1 - Additional network section added
--1.0 - Initial Release

--ZEBRA-MIB { iso org(3) dod(6) internet(1) private(4) enterprises(1) 10642 }

ZEBRA-MIB DEFINITIONS ::= BEGIN

IMPORTS
  MODULE-IDENTITY,
  OBJECT-TYPE,
  Unsigned32,
  TimeTicks,
  IpAddress,
  enterprises                          FROM SNMPv2-SMI
  DisplayString,
  PhysAddress                          FROM SNMPv2-TC;

zebraMib MODULE-IDENTITY
       LAST-UPDATED "202401220000Z"
       ORGANIZATION "Zebra Technologies Corp."
       CONTACT-INFO
               "        Zebra Technologies Corporation

                Postal: 3 Overlook Point, Lincolnshire, Illinois, USA 60069

                   Tel: +1 877 275 9327

                E-mail: support@zebra.com"

       DESCRIPTION
               "The MIB module for Zebra Technologies Link-OS Devices"
      
       REVISION "202401220000Z"
       DESCRIPTION
               "9 - Link-OS 6.x Updates (zbrTrackedAlertsCode,zbrOptUnsAlertsCondition,...) additions (zbrEzplTakeLabelCalibration,zbrMediaLinerlessOffset,zbrCutter,...)"
       REVISION "202309270000Z"               
       DESCRIPTION
               "8 - Link-OS 6.8 wireless security settings,"
       REVISION "202110120001Z"
       DESCRIPTION
               "7 - Link-OS 6.7 Updates mqtt, additions generateStatusAlerts"
       REVISION "202110120000Z"
       DESCRIPTION
               "6 - Link-OS 6.5 Update zbrWLanSecurUserName length, additions (zbrBluetoothDisconnectIdleLink, zbrBluetoothSniffModeEnable, zbrControlReprint)"
       REVISION "202102090000Z"
       DESCRIPTION
               "5 - Link-OS 6.4 additions (zbrPrintXiCompatibilityAdjust)"
       REVISION "202007150000Z"
       DESCRIPTION
               "4 - Link-OS 6.3 Updates zbrTrackedAlertsTable to include alert clearing, additions (zbrDeviceResetButtonEnable, zbrWLanSetupDhcpRequired, zbrAplSettings, ...)"
       REVISION "202005220000Z"
       DESCRIPTION
               "Link-OS 6.2 additions (zbrOdometerNetRibbonUse, zbrOdometerNetMediaUse, zbrTrackedAlertsTable, zbrSuppliesMediaCartTable, zbrSuppliesRibbonCartTable, ...)"
       REVISION "201707180000Z"
       DESCRIPTION
               "Link-OS 4,5 additions (LinkOSConnector,TLS, HTTPS, Firewall,platform features,..) removal (zbrTcpSecurityTable, zbrTcpMLPTable)"
       REVISION "201408010000Z"
       DESCRIPTION
               "LINK-OS 3.0 additions (Ntp, ...)"
       REVISION "201210030000Z"
       DESCRIPTION
               "LINK-OS     additions (Weblink, CaptureData, ..)"
       REVISION "201201230000Z"
       DESCRIPTION
               "3 - Expanding coverage (wireless, bluetooth, serial, ...)"
       REVISION "201012130001Z"
       DESCRIPTION
               "1.1 - Additional network section added"
       REVISION "201012130000Z"
       DESCRIPTION
               "1.0 - Initial Release"

       ::= { zebra 100 }




--===========================
-- zebra object identifiers
--===========================
zebra                                OBJECT IDENTIFIER ::= { enterprises 10642 }
zbrGeneralInfo                       OBJECT IDENTIFIER ::= { zebra 1 }
zbrGenGeoLocation                    OBJECT IDENTIFIER ::= { zbrGeneralInfo 30 }
zbrPlatform                          OBJECT IDENTIFIER ::= { zebra 2 }
zbrHead                              OBJECT IDENTIFIER ::= { zbrPlatform 1 }
zbrDisplay                           OBJECT IDENTIFIER ::= { zbrPlatform 2 }
zbrDisplayLines                      OBJECT IDENTIFIER ::= { zbrDisplay 1 }
zbrDisplayPassword                   OBJECT IDENTIFIER ::= { zbrDisplay 14 }
zbrPower                             OBJECT IDENTIFIER ::= { zbrPlatform 3 }
zbrPowerLowBatteryAlert              OBJECT IDENTIFIER ::= { zbrPower 4 }
zbrSleep                             OBJECT IDENTIFIER ::= { zbrPower 50 }
zbrEnergyStar                        OBJECT IDENTIFIER ::= { zbrPower 60 }
zbrPdl                               OBJECT IDENTIFIER ::= { zbrPlatform 10 }
zbrCpcl                              OBJECT IDENTIFIER ::= { zbrPdl 2 }
zbrZpl                               OBJECT IDENTIFIER ::= { zbrPdl 3 }
zbrEzpl                              OBJECT IDENTIFIER ::= { zbrPdl 4 }
zbrOptions                           OBJECT IDENTIFIER ::= { zebra 3 }
zbrOdometer                          OBJECT IDENTIFIER ::= { zbrOptions 1 }
zbrRtc                               OBJECT IDENTIFIER ::= { zbrOptions 2 }
zbrOptUnsolictedAlerts               OBJECT IDENTIFIER ::= { zbrOptions 30 }
zbrOptUnsAlrtTrackedSettings         OBJECT IDENTIFIER ::= { zbrOptUnsolictedAlerts 30 }
zbrOptUnsAlrtHttp                    OBJECT IDENTIFIER ::= { zbrOptUnsolictedAlerts 40 }
zbrOptUnsAlrtLogging                 OBJECT IDENTIFIER ::= { zbrOptUnsAlrtHttp 10 }
zbrOptUnsAlrtAuthentication          OBJECT IDENTIFIER ::= { zbrOptUnsAlrtHttp 15 }
zbrMagCardReader                     OBJECT IDENTIFIER ::= { zbrOptions 35 }
zbrRfid                              OBJECT IDENTIFIER ::= { zbrOptions 40 }
zbrRfidPos                           OBJECT IDENTIFIER ::= { zbrRfid 4 }
zbrRfidErrorResponse                 OBJECT IDENTIFIER ::= { zbrRfid 5 }
zbrRfidRdr1                          OBJECT IDENTIFIER ::= { zbrRfid 6 }
zbrRfidHostLog                       OBJECT IDENTIFIER ::= { zbrRfid 20 }
zbrRfidRdr1Pwr                       OBJECT IDENTIFIER ::= { zbrRfidRdr1 5 }
zbrRfidRdr1Tag                       OBJECT IDENTIFIER ::= { zbrRfidRdr1 6 }
zbrRfidRdr1TagRd                     OBJECT IDENTIFIER ::= { zbrRfidRdr1Tag 4 }
zbrRfidRdr1TagTest                   OBJECT IDENTIFIER ::= { zbrRfidRdr1Tag 5 }
zbrCradle                            OBJECT IDENTIFIER ::= { zbrOptions 41 }
zbrCradleComm                        OBJECT IDENTIFIER ::= { zbrCradle 1 }
zbrNetmanage                         OBJECT IDENTIFIER ::= { zebra 5 }
zbrMirror                            OBJECT IDENTIFIER ::= { zbrNetmanage 1 }
zbrMirrorFeedback                    OBJECT IDENTIFIER ::= { zbrMirror 20 }
zbrPrint                             OBJECT IDENTIFIER ::= { zebra 6 }
zbrControl                           OBJECT IDENTIFIER ::= { zebra 7 }
zbrSettings                          OBJECT IDENTIFIER ::= { zebra 8 }
zbrSettingsMediaFeed                 OBJECT IDENTIFIER ::= { zbrSettings 40 }
zbrSettingsSensors                   OBJECT IDENTIFIER ::= { zbrSettings 41 }
zbrSettingsSensorBar                 OBJECT IDENTIFIER ::= { zbrSettingsSensors 1 }
zbrSettingsSensorGap                 OBJECT IDENTIFIER ::= { zbrSettingsSensors 2 }
zbrSettingsSensorRibbon              OBJECT IDENTIFIER ::= { zbrSettingsSensors 3 }
zbrSettingsSensorSelfAdjusting       OBJECT IDENTIFIER ::= { zbrSettingsSensors 4 }
zbrFile                              OBJECT IDENTIFIER ::= { zebra 9 }
zbrFileCert                          OBJECT IDENTIFIER ::= { zbrFile 30 }
zbrDevice                            OBJECT IDENTIFIER ::= { zebra 10 }
zbrLight                             OBJECT IDENTIFIER ::= { zbrDevice 10 }
zbrSyslog                            OBJECT IDENTIFIER ::= { zbrDevice 11 }
zbrFeature                           OBJECT IDENTIFIER ::= { zbrDevice 12 }
zbrAlerts                            OBJECT IDENTIFIER ::= { zbrDevice 13 }
zbrMcu                               OBJECT IDENTIFIER ::= { zbrDevice 15 }
zbrMcuComm                           OBJECT IDENTIFIER ::= { zbrDevice 17 }
zbrMcuCutter                         OBJECT IDENTIFIER ::= { zbrDevice 19 }
zbrMcuIoExpander                     OBJECT IDENTIFIER ::= { zbrDevice 22 }
zbrPrinthead                         OBJECT IDENTIFIER ::= { zbrDevice 28 }
zbrPrintheadTest                     OBJECT IDENTIFIER ::= { zbrPrinthead 29 }
zbrApplicator                        OBJECT IDENTIFIER ::= { zbrDevice 30 }
zbrFips                              OBJECT IDENTIFIER ::= { zbrDevice 33 }
zbrSensor                            OBJECT IDENTIFIER ::= { zebra 15 }
zbrSensorPeel                        OBJECT IDENTIFIER ::= { zbrSensor 1 }
zbrSensorWidth                       OBJECT IDENTIFIER ::= { zbrSensor 2 }
zbrSensorGap                         OBJECT IDENTIFIER ::= { zbrSensor 3 }
zbrSensorBackBar                     OBJECT IDENTIFIER ::= { zbrSensor 4 }
zbrSensorFrontBar                    OBJECT IDENTIFIER ::= { zbrSensor 5 }
zbrSensorHead                        OBJECT IDENTIFIER ::= { zbrSensor 6 }
zbrSensorBattery                     OBJECT IDENTIFIER ::= { zbrSensor 7 }
zbrSensorAmbientTemp                 OBJECT IDENTIFIER ::= { zbrSensor 8 }
zbrSensorAmbientHumidity             OBJECT IDENTIFIER ::= { zbrSensor 9 }
zbrSensorProximity                   OBJECT IDENTIFIER ::= { zbrSensor 10 }
zbrSensorAmbientLight                OBJECT IDENTIFIER ::= { zbrSensor 11 }
zbrSensorAirPressure                 OBJECT IDENTIFIER ::= { zbrSensor 12 }
zbrSensorMagnetometer                OBJECT IDENTIFIER ::= { zbrSensor 13 }
zbrSensorObjectTemperature           OBJECT IDENTIFIER ::= { zbrSensor 14 }
zbrInterfaces                        OBJECT IDENTIFIER ::= { zebra 20 }
zbrComm                              OBJECT IDENTIFIER ::= { zbrInterfaces 1 }
zbrBluetooth                         OBJECT IDENTIFIER ::= { zbrInterfaces 3 }
zbrBluetoothLowEnergy                OBJECT IDENTIFIER ::= { zbrBluetooth 50 }
zbrParallelPort                      OBJECT IDENTIFIER ::= { zbrInterfaces 5 }
zbrIfWirelessLan                     OBJECT IDENTIFIER ::= { zbrInterfaces 6 }
zbrWLanStatus                        OBJECT IDENTIFIER ::= { zbrIfWirelessLan 1 }
zbrWLanSettings                      OBJECT IDENTIFIER ::= { zbrIfWirelessLan 2 }
zbrWLanRoaming                       OBJECT IDENTIFIER ::= { zbrWLanSettings 30 }
zbrWLanKeepAlive                     OBJECT IDENTIFIER ::= { zbrWLanSettings 31 }
zbrWLanElevenN                       OBJECT IDENTIFIER ::= { zbrWLanSettings 32 }
zbrWLanElevenAC                      OBJECT IDENTIFIER ::= { zbrWLanSettings 33 }
zbrWLanSecurity                      OBJECT IDENTIFIER ::= { zbrIfWirelessLan 3 }
zbrWLanWaveAgent                     OBJECT IDENTIFIER ::= { zbrIfWirelessLan 10 }
zbrWLanCcx                           OBJECT IDENTIFIER ::= { zbrIfWirelessLan 20 }
zbrWLanIpv6                          OBJECT IDENTIFIER ::= { zbrIfWirelessLan 30 }
zbrWLanIpv6Dhcp                      OBJECT IDENTIFIER ::= { zbrWLanIpv6 20 }
zbrWLanIpv6Static                    OBJECT IDENTIFIER ::= { zbrWLanIpv6 21 }
zbrNetwork                           OBJECT IDENTIFIER ::= { zbrInterfaces 10 }
zbrNetCommands                       OBJECT IDENTIFIER ::= { zbrNetwork 5 }
zbrNetCommonNetworkSettings          OBJECT IDENTIFIER ::= { zbrNetwork 10 }
zbrNetProtocols                      OBJECT IDENTIFIER ::= { zbrNetCommonNetworkSettings 5 }
zbrNetProtoTcp                       OBJECT IDENTIFIER ::= { zbrNetProtocols 5 }
zbrNetProtoFtp                       OBJECT IDENTIFIER ::= { zbrNetProtocols 6 }
zbrNetProtoLpd                       OBJECT IDENTIFIER ::= { zbrNetProtocols 7 }
zbrNetProtoMail                      OBJECT IDENTIFIER ::= { zbrNetProtocols 8 }
zbrNetProtoSmtp                      OBJECT IDENTIFIER ::= { zbrNetProtoMail 5 }
zbrNetProtoPop3                      OBJECT IDENTIFIER ::= { zbrNetProtoMail 6 }
zbrNetProtoUdp                       OBJECT IDENTIFIER ::= { zbrNetProtocols 10 }
zbrNetProtoHttp                      OBJECT IDENTIFIER ::= { zbrNetProtocols 11 }
zbrNetProtoSnmp                      OBJECT IDENTIFIER ::= { zbrNetProtocols 12 }
zbrNetProtoNtp                       OBJECT IDENTIFIER ::= { zbrNetProtocols 13 }
zbrNetProtoTls                       OBJECT IDENTIFIER ::= { zbrNetProtocols 14 }
zbrNetProtoHttps                     OBJECT IDENTIFIER ::= { zbrNetProtocols 15 }
zbrNetProtoMqtt                      OBJECT IDENTIFIER ::= { zbrNetProtocols 16 }
zbrNetProtoMqttConn1                 OBJECT IDENTIFIER ::= { zbrNetProtoMqtt 20 }
zbrNetProtoMqttConn2                 OBJECT IDENTIFIER ::= { zbrNetProtoMqtt 21 }
zbrNetProtoMqttLogging               OBJECT IDENTIFIER ::= { zbrNetProtoMqtt 22 }
zbrNetProtoSnmpv3                    OBJECT IDENTIFIER ::= { zbrNetProtocols 17 }
zbrNetProtoSnmpv3Admin               OBJECT IDENTIFIER ::= { zbrNetProtoSnmpv3 2 }
zbrNetProtoSnmpv3Monitor             OBJECT IDENTIFIER ::= { zbrNetProtoSnmpv3 3 }
zbrNetJetAdmin                       OBJECT IDENTIFIER ::= { zbrNetCommonNetworkSettings 6 }
zbrNetDhcp                           OBJECT IDENTIFIER ::= { zbrNetCommonNetworkSettings 7 }
zbrNetFirewall                       OBJECT IDENTIFIER ::= { zbrNetCommonNetworkSettings 8 }
zbrNetFirewallAuth                   OBJECT IDENTIFIER ::= { zbrNetFirewall 20 }
zbrNetInterfaceSpecificSettings      OBJECT IDENTIFIER ::= { zbrNetwork 20 }
zbrNetIfGeneral                      OBJECT IDENTIFIER ::= { zbrNetInterfaceSpecificSettings 5 }
zbrNetIfDhcp                         OBJECT IDENTIFIER ::= { zbrNetInterfaceSpecificSettings 10 }
zbrNetIfTcp                          OBJECT IDENTIFIER ::= { zbrNetInterfaceSpecificSettings 15 }
zbrInternalWired                     OBJECT IDENTIFIER ::= { zbrInterfaces 11 }
zbrIWired8021x                       OBJECT IDENTIFIER ::= { zbrInternalWired 20 }
zbrIWiredIpv6                        OBJECT IDENTIFIER ::= { zbrInternalWired 21 }
zbrIWiredIpv6Dhcp                    OBJECT IDENTIFIER ::= { zbrIWiredIpv6 20 }
zbrIWiredIpv6Static                  OBJECT IDENTIFIER ::= { zbrIWiredIpv6 21 }
zbrSerialNumbers                     OBJECT IDENTIFIER ::= { zebra 21 }
zbrJobLogging                        OBJECT IDENTIFIER ::= { zebra 30 }
zbrDataCapture                       OBJECT IDENTIFIER ::= { zebra 31 }
zbrDCapChannel1                      OBJECT IDENTIFIER ::= { zbrDataCapture 1 }
zbrDCapChan1Data                     OBJECT IDENTIFIER ::= { zbrDCapChannel1 10 }
zbrWeblink                           OBJECT IDENTIFIER ::= { zebra 32 }
zbrWeblinkLogging                    OBJECT IDENTIFIER ::= { zbrWeblink 10 }
zbrWeblinkCloudConnect               OBJECT IDENTIFIER ::= { zbrWeblink 20 }
zbrWeblinkConn1                      OBJECT IDENTIFIER ::= { zbrWeblink 30 }
zbrWeblinkConn1Authentication        OBJECT IDENTIFIER ::= { zbrWeblinkConn1 15 }
zbrWeblinkConn1Test                  OBJECT IDENTIFIER ::= { zbrWeblinkConn1 20 }
zbrWeblinkConn2                      OBJECT IDENTIFIER ::= { zbrWeblink 31 }
zbrWeblinkConn2Authentication        OBJECT IDENTIFIER ::= { zbrWeblinkConn2 15 }
zbrWeblinkConn2Test                  OBJECT IDENTIFIER ::= { zbrWeblinkConn2 20 }
zbrBasicInterpreter                  OBJECT IDENTIFIER ::= { zebra 40 }
zbrZbiStartInfo                      OBJECT IDENTIFIER ::= { zbrBasicInterpreter 10 }
zbrZbiControl                        OBJECT IDENTIFIER ::= { zbrBasicInterpreter 20 }
zbrUsbHost                           OBJECT IDENTIFIER ::= { zebra 41 }
zbrUsbMirror                         OBJECT IDENTIFIER ::= { zebra 42 }
zbrUsbOtg                            OBJECT IDENTIFIER ::= { zebra 43 }
zbrUsbMirrorFeedback                 OBJECT IDENTIFIER ::= { zbrUsbMirror 12 }
zbrApl                               OBJECT IDENTIFIER ::= { zebra 45 }
zbrAplI                              OBJECT IDENTIFIER ::= { zbrApl 5 }
zbrAplD                              OBJECT IDENTIFIER ::= { zbrApl 7 }
zbrNfc                               OBJECT IDENTIFIER ::= { zebra 46 }
zbrRibbon                            OBJECT IDENTIFIER ::= { zebra 47 }
zbrCartridge                         OBJECT IDENTIFIER ::= { zbrRibbon 1 }
zbrSupplies                          OBJECT IDENTIFIER ::= { zebra 48 }
zbrSuppliesMedia                     OBJECT IDENTIFIER ::= { zbrSupplies 1 }
zbrSuppliesRibbon                    OBJECT IDENTIFIER ::= { zbrSupplies 2 }
zbrLinkOs                            OBJECT IDENTIFIER ::= { zebra 49 }
zbrLinkOsConnector                   OBJECT IDENTIFIER ::= { zbrLinkOs 1 }
zbrMedia                             OBJECT IDENTIFIER ::= { zebra 50 }
zbrMediaCartridge                    OBJECT IDENTIFIER ::= { zbrMedia 1 }
zbrCutter                            OBJECT IDENTIFIER ::= { zebra 51 }




--=====================
-- zebra.zbrGeneralInfo
--=====================
zbrGeneralModel OBJECT-TYPE
    SYNTAX DisplayString (SIZE (0..20))
    MAX-ACCESS read-only
    STATUS current
    DESCRIPTION
    "Printer Model"
    ::= { zbrGeneralInfo 1 }

zbrGeneralFirmwareVersion OBJECT-TYPE
    SYNTAX DisplayString (SIZE (0..20))
    MAX-ACCESS read-only
    STATUS current
    DESCRIPTION
    "Version of the firmware currently on the printer."
    ::= { zbrGeneralInfo 2 }

zbrGeneralPlugAndPlayString OBJECT-TYPE
    SYNTAX DisplayString (SIZE (0..120))
    MAX-ACCESS read-only
    STATUS current
    DESCRIPTION
    "Plug-n-Play String"
    ::= { zbrGeneralInfo 3 }

zbrGeneralName OBJECT-TYPE
    SYNTAX DisplayString (SIZE (0..17))
    MAX-ACCESS read-write
    STATUS current
    DESCRIPTION
    "Printer Name"
    ::= { zbrGeneralInfo 4 }

zbrGeneralDescription OBJECT-TYPE
    SYNTAX DisplayString (SIZE (0..128))
    MAX-ACCESS read-write
    STATUS current
    DESCRIPTION
    "Printer Description"
    ::= { zbrGeneralInfo 5 }

zbrGeneralMibVersion OBJECT-TYPE
    SYNTAX INTEGER
    MAX-ACCESS read-only
    STATUS current
    DESCRIPTION
    "MIB Version"
    ::= { zbrGeneralInfo 6 }

zbrGeneralBootblock OBJECT-TYPE
    SYNTAX DisplayString (SIZE (0..100))
    MAX-ACCESS read-only
    STATUS current
    DESCRIPTION
    "Boot Block"
    ::= { zbrGeneralInfo 7 }

zbrGeneralPlugAndPlayOption OBJECT-TYPE
    SYNTAX INTEGER {
        cpcl(1),
        zpl(2),
        epl(3)
    }
    MAX-ACCESS read-write
    STATUS current
    DESCRIPTION
    "Plug-n-Play Option."
    ::= { zbrGeneralInfo 8 }

zbrGeneralUniqueId OBJECT-TYPE
    SYNTAX DisplayString (SIZE (0..14))
    MAX-ACCESS read-only
    STATUS current
    DESCRIPTION
    "Unique Id"
    ::= { zbrGeneralInfo 9 }

zbrGeneralDeviceIdString OBJECT-TYPE
    SYNTAX DisplayString (SIZE (0..255))
    MAX-ACCESS read-only
    STATUS current
    DESCRIPTION
    "Device Id String"
    ::= { zbrGeneralInfo 10 }

zbrGeneralCompanyName OBJECT-TYPE
    SYNTAX  DisplayString (SIZE (0..255))
    MAX-ACCESS  read-write
    STATUS  current
    DESCRIPTION
    "A string indicating the manufacturer of the device."
    ::= { zbrGeneralInfo 11 }

zbrGeneralCompanyLoc OBJECT-TYPE
    SYNTAX  DisplayString (SIZE (0..30))
    MAX-ACCESS  read-only
    STATUS  current
    DESCRIPTION
    "A string indicating the location of the manufacturer
    of the device."
    ::= { zbrGeneralInfo 12 }

zbrGeneralCompanyPhone OBJECT-TYPE
    SYNTAX  DisplayString (SIZE (0..128))
    MAX-ACCESS  read-write
    STATUS  current
    DESCRIPTION
    "A string indicating the phone number of the
    manufacturer of the device."
    ::= { zbrGeneralInfo 13 }

zbrGeneralCompanyTechSupport OBJECT-TYPE
    SYNTAX  DisplayString (SIZE (0..255))
    MAX-ACCESS  read-write
    STATUS  current
    DESCRIPTION
    "A string indicating the technical support information
    for the device."
    ::= { zbrGeneralInfo 14 }

zbrGeneralCompanyHomeUrl OBJECT-TYPE
    SYNTAX  DisplayString (SIZE (0..255))
    MAX-ACCESS  read-write
    STATUS  current
    DESCRIPTION
    "A string indicating the company's home URL for the device."
    ::= { zbrGeneralInfo 15 }

zbrGeneralDateCode OBJECT-TYPE
    SYNTAX  DisplayString (SIZE (0..10))
    MAX-ACCESS  read-only
    STATUS  current
    DESCRIPTION
    "The device's datecode."
    ::= { zbrGeneralInfo 16 }

zbrGeneralHostIdentification OBJECT-TYPE
    SYNTAX  DisplayString (SIZE (0..255))
    MAX-ACCESS  read-only
    STATUS  current
    DESCRIPTION
    "The device host identification string."
    ::= { zbrGeneralInfo 17 }

zbrGeneralLINKOSVersion OBJECT-TYPE
    SYNTAX  DisplayString (SIZE (0..7))
    MAX-ACCESS  read-only
    STATUS  current
    DESCRIPTION
    "The LINK-OS version string."
    ::= { zbrGeneralInfo 18 }

zbrGeneralSubmodel OBJECT-TYPE
    SYNTAX DisplayString (SIZE (0..20))
    MAX-ACCESS read-only
    STATUS current
    DESCRIPTION
    "Printer Submodel"
    ::= { zbrGeneralInfo 19 }
    
    
zbrGeneralProtectedModeEnabled OBJECT-TYPE
   SYNTAX  INTEGER {
      on(1),
      off(2)
   }
   MAX-ACCESS read-only
   STATUS current
   DESCRIPTION
   "State of settings protected mode feature."
   ::= { zbrGeneralInfo 21 }
   
zbrGeneralAllowFirmwareDownloads OBJECT-TYPE
   SYNTAX  INTEGER {
      yes(1),
      no(2)
   }
   MAX-ACCESS read-write
   STATUS current
   DESCRIPTION
   "Whether firmware downloads are allowed or not."
   ::= { zbrGeneralInfo 22 }
   
zbrGeneralProtectedModeAllowed OBJECT-TYPE
   SYNTAX  INTEGER {
      yes(1),
      no(2)
   }
   MAX-ACCESS read-only
   STATUS current
   DESCRIPTION
   "Whether protected mode is allowed or not."
   ::= { zbrGeneralInfo 23 }
   
zbrGeneralCompanyModelName OBJECT-TYPE
   SYNTAX  DisplayString (SIZE (0..255))
   MAX-ACCESS  read-write
   STATUS  current
   DESCRIPTION
   "A string indicating the company's model name for the device."
   ::= { zbrGeneralInfo 24 }
   
zbrGeneralLinkOSVersionFull OBJECT-TYPE
   SYNTAX  DisplayString (SIZE (0..30))
   MAX-ACCESS  read-only
   STATUS  current
   DESCRIPTION
   "The full Link-OS version string."
   ::= { zbrGeneralInfo 25 }

zbrGeneralMibBase OBJECT-TYPE
    SYNTAX  OBJECT IDENTIFIER
    MAX-ACCESS read-only
    STATUS current
    DESCRIPTION
    "Mib Base"
    ::= { zbrGeneralInfo 100 }

--=====================
-- zebra.zbrGeneralInfo.zbrGenGeoLocation
--=====================
zbrGenGeoLatitude OBJECT-TYPE
   SYNTAX DisplayString (SIZE (1..10))
   MAX-ACCESS read-write
   STATUS current
   DESCRIPTION
   "The geographic latitudinal position. The value is returned with 6 decimal places.
   A value of 0.000001 degrees is on the order of 0.1 meter of distance on the earth's surface."
   ::= { zbrGenGeoLocation 1 }

zbrGenGeoLongitude OBJECT-TYPE
   SYNTAX DisplayString (SIZE (1..11))
   MAX-ACCESS read-write
   STATUS current
   DESCRIPTION
   "The geographic longitudinal position. The value is returned with 6 decimal places.
   A value of 0.000001 degrees is on the order of no more than 0.1 meter of distance on the earth's surface."
   ::= { zbrGenGeoLocation 2 }

zbrGenGeoAltitude OBJECT-TYPE
   SYNTAX DisplayString (SIZE (1..16))
   MAX-ACCESS read-write
   STATUS current
   DESCRIPTION
   "The altitude in meters above sea level. The value is returned with 6 decimal places.
   Positive values are above sea level and negative values are below sea level."
   ::= { zbrGenGeoLocation 3 }

zbrGenGeoAccuracy OBJECT-TYPE
   SYNTAX DisplayString (SIZE (1..16))
   MAX-ACCESS read-write
   STATUS current
   DESCRIPTION
   "The accuracy in meters of the geographic position values. The value is returned with 6 decimal places."
   ::= { zbrGenGeoLocation 4 }

--===========================
-- zebra.zbrPlatform.zbrHead
--===========================

zbrHeadLatch OBJECT-TYPE
    SYNTAX INTEGER {
        ok(1),
        open(2)
    }
   MAX-ACCESS read-only
   STATUS current
   DESCRIPTION
   "The status of the printer head latch.
   The head latch must be closed for printing."
   ::= { zbrHead 1 }

zbrHeadDotsPerMm OBJECT-TYPE
    SYNTAX INTEGER
    MAX-ACCESS read-only
    STATUS current
    DESCRIPTION
    "Dots per mm"
    ::= { zbrHead 2 }

zbrHeadDotsPerDotrow OBJECT-TYPE
    SYNTAX INTEGER
    MAX-ACCESS read-only
    STATUS current
    DESCRIPTION
    "Dots per Dotrow"
    ::= { zbrHead 3 }

zbrHeadPrintheadTemp OBJECT-TYPE
    SYNTAX INTEGER
    MAX-ACCESS read-only
    STATUS current
    DESCRIPTION
    "Printhead Temperature"
    ::= { zbrHead 4 }

zbrHeadPrintheadOvertempThreshold OBJECT-TYPE
    SYNTAX INTEGER
    MAX-ACCESS read-only
    STATUS current
    DESCRIPTION
    "Printhead Overtemp Threshold"
    ::= { zbrHead 5 }

zbrHeadPrintheadUndertempThreshold OBJECT-TYPE
    SYNTAX INTEGER
    MAX-ACCESS read-only
    STATUS current
    DESCRIPTION
    "Printhead Undertemp Threshold"
    ::= { zbrHead 6 }

zbrHeadUndertempWarning OBJECT-TYPE
    SYNTAX  INTEGER {
        no(1),
        yes(2)
    }
    MAX-ACCESS read-only
    STATUS current
    DESCRIPTION
   "Head Under Temperature Error"
    ::= { zbrHead 7 }

zbrHeadOvertempError OBJECT-TYPE
    SYNTAX  INTEGER {
        no(1),
        yes(2)
    }
    MAX-ACCESS read-only
    STATUS current
    DESCRIPTION
   "Head Over Temperature Error"
   ::= { zbrHead 8 }

--=================================================================================================
--darknessSwitch deprecated as of EPOCH_RELOADED (Evo6ULL) and going forward 
--(Dec. 2019)
-- brought back for Evo6ULL as read-write (Feb. 2020)
--=================================================================================================
zbrHeadDarknessSwitch OBJECT-TYPE
    SYNTAX  INTEGER {
        low(1),
        medium(2),
        high(3)
    }
    MAX-ACCESS  read-write
    STATUS  current
    DESCRIPTION
     "Darkness Switch Value"
     ::= { zbrHead 9 }

zbrHeadDotsPerInch OBJECT-TYPE
    SYNTAX INTEGER
    MAX-ACCESS read-only
    STATUS current
    DESCRIPTION
    "Printhead resolution in dots per inch."
    ::= { zbrHead 10 }

--=================================================================================================
--darknessSwitchEnable deprecated as of EPOCH_RELOADED (Evo6ULL) and going forward 
--(Dec. 2019)
-- brought back for Evo6ULL (Feb. 2020)
--=================================================================================================
zbrHeadDarknessSwitchEnable OBJECT-TYPE
   SYNTAX INTEGER {
      on(1),
      off(2)
   }
   MAX-ACCESS read-write
   STATUS current
   DESCRIPTION
   "Enable[on] or disable[off] the Darkness Switch"
   ::= { zbrHead 11 }

zbrHeadAuthenticated OBJECT-TYPE
    SYNTAX INTEGER {
        yes(1),
        no(2)
    }
   MAX-ACCESS read-only
   STATUS current
   DESCRIPTION
   "The status of the printhead authentication."
   ::= { zbrHead 12 }
   
zbrHeadType OBJECT-TYPE
   SYNTAX INTEGER (0..12)
   MAX-ACCESS read-write
   STATUS current
   DESCRIPTION
   "Get or Set the type of printhead currently installed."
   ::= { zbrHead 13 } 

--===========================
-- zebra.zbrPlatform.zbrDisplay
--===========================

zbrDisplayLinesLine1 OBJECT-TYPE
    SYNTAX DisplayString (SIZE (0..255))
    MAX-ACCESS  read-write
    STATUS  current
    DESCRIPTION
    "Text to replace line 1 of the lcd display."
    ::= { zbrDisplayLines 1 }

zbrDisplayLinesLine2 OBJECT-TYPE
    SYNTAX DisplayString (SIZE (0..255))
    MAX-ACCESS  read-write
    STATUS  current
    DESCRIPTION
    "Text to replace line 2 of the lcd display."
    ::= { zbrDisplayLines 2 }

zbrDisplayLinesLine3 OBJECT-TYPE
    SYNTAX DisplayString (SIZE (0..255))
    MAX-ACCESS  read-write
    STATUS  current
    DESCRIPTION
    "Text to replace line 3 of the lcd display."
    ::= { zbrDisplayLines 3 }

zbrDisplayLinesLine4 OBJECT-TYPE
    SYNTAX DisplayString (SIZE (0..255))
    MAX-ACCESS  read-write
    STATUS  current
    DESCRIPTION
    "Text to replace line 4 of the lcd display."
    ::= { zbrDisplayLines 4 }

zbrDisplayXml OBJECT-TYPE
    SYNTAX OCTET STRING (SIZE (0..10000))
    MAX-ACCESS read-only
    STATUS current
    DESCRIPTION
    "Frontpanel xml"
    ::= { zbrDisplay 2 }

zbrDisplayBatteryAlertsAlwaysDisplayed OBJECT-TYPE
    SYNTAX INTEGER {
        on(1),
        off(2)
    }
    MAX-ACCESS read-write
    STATUS current
    DESCRIPTION
    "Battery Alerts Always Displayed"
    ::= { zbrDisplay 3 }

zbrDisplayContrast OBJECT-TYPE
   SYNTAX INTEGER (3..15)
   MAX-ACCESS read-write
   STATUS current
   DESCRIPTION
   "The contrast level on the printer's display."
   ::= { zbrDisplay 5 }

zbrDisplayText OBJECT-TYPE
   SYNTAX OCTET STRING (SIZE (0..2047))
   MAX-ACCESS read-write
   STATUS current
   DESCRIPTION
   "All the lines of text on the printer's display."
   ::= { zbrDisplay 6 }

zbrDisplayBacklight OBJECT-TYPE
    SYNTAX INTEGER {
        on(1),
        off(2)
    }
   MAX-ACCESS read-write
   STATUS current
   DESCRIPTION
   "Backlight control."
   ::= { zbrDisplay 7 }

zbrDisplayBacklightOnTime OBJECT-TYPE
   SYNTAX INTEGER (0..8191)
   MAX-ACCESS read-write
   STATUS current
   DESCRIPTION
   "Amount of time before the backlight turns off in seconds."
   ::= { zbrDisplay 8 }

zbrIdleDisplayFormat OBJECT-TYPE
   SYNTAX INTEGER {
      fw-version (1),
      ip-address (2),
      mm-dd-yyyy-24-hr (3),
      mm-dd-yyyy-12-hr (4),
      dd-mm-yyyy-24-hr (5),
      dd-mm-yyyy-12-hr (6)
   }
   MAX-ACCESS read-write
   STATUS current
   DESCRIPTION
   "The idle display format."
   ::= { zbrDisplay 9 }


zbrIdleDisplayValue OBJECT-TYPE
   SYNTAX DisplayString (SIZE (0..255))
   MAX-ACCESS read-only
   STATUS current
   DESCRIPTION
   "The idle display value."
   ::= { zbrDisplay 10 }


zbrDisplayRootWml OBJECT-TYPE
   SYNTAX DisplayString (SIZE (0..128))
   MAX-ACCESS read-write
   STATUS current
   DESCRIPTION
   "The root WML to use."
   ::= { zbrDisplay 13 }

zbrDisplayPasswordCurrent OBJECT-TYPE
    SYNTAX DisplayString (SIZE (0..255))
    MAX-ACCESS  read-write
    STATUS  current
    DESCRIPTION
    "contains the current password value (protected)."
    ::= { zbrDisplayPassword 1 }   
   
zbrDisplayPasswordType OBJECT-TYPE
    SYNTAX INTEGER {
        numeric(1)
    }
   MAX-ACCESS read-write
   STATUS current
   DESCRIPTION
   "The password type."
   ::= { zbrDisplayPassword 2 }

zbrDisplayPasswordInput OBJECT-TYPE
    SYNTAX DisplayString (SIZE (0..128))
    MAX-ACCESS  read-write
    STATUS  current
    DESCRIPTION
    "contains the inputted password value."
    ::= { zbrDisplayPassword 3 }
    
zbrDisplayPasswordLength OBJECT-TYPE
    SYNTAX INTEGER (1..20)
    MAX-ACCESS  read-write
    STATUS  current
    DESCRIPTION
    "contains the inputted password value."
    ::= { zbrDisplayPassword 4 }    
    

zbrDisplayLanguage OBJECT-TYPE
    SYNTAX DisplayString (SIZE (0..128))
    MAX-ACCESS  read-write
    STATUS  current
    DESCRIPTION
    "bufToDisplayString, Current display language."
    ::= { zbrDisplay 15 }

zbrDisplayLoadCard OBJECT-TYPE
    SYNTAX DisplayString (SIZE (0..128))
    MAX-ACCESS  read-write
    STATUS  current
    DESCRIPTION
    "WML card to load."
    ::= { zbrDisplay 16 }
    
zbrDisplayStatusBarSuppress OBJECT-TYPE
   SYNTAX INTEGER {
        on(1),
        off(2)
    }
   MAX-ACCESS read-write
   STATUS current
   DESCRIPTION
   "Suppress display of the status bar."
   ::= { zbrDisplay 17 }
   
zbrDisplaySuppressAllAlerts OBJECT-TYPE
   SYNTAX INTEGER {
        on(1),
        off(2)
    }
   MAX-ACCESS read-write
   STATUS current
   DESCRIPTION
   "Suppress all displayed alerts."
   ::= { zbrDisplay 18 }

zbrDisplayPasswordLevel OBJECT-TYPE
    SYNTAX DisplayString (SIZE (0..128))
    MAX-ACCESS  read-write
    STATUS  current
    DESCRIPTION
    "The Password Level"
    ::= { zbrDisplay 19 }
       
zbrDisplayBatchCounter OBJECT-TYPE
   SYNTAX INTEGER {
      enabled(1),
      disabled(2)
   }
   MAX-ACCESS read-write
   STATUS current
   DESCRIPTION
    "Enable or disable the batch counter alert display"
   ::= { zbrDisplay 20 }

zbrDisplayCalibration OBJECT-TYPE
    SYNTAX INTEGER {
        on(1),
        off(2)
    }
   MAX-ACCESS read-write
   STATUS current
   DESCRIPTION
   " Activate touch panel calibration mode"
   ::= { zbrDisplay 21 }

zbrDisplayOrientation OBJECT-TYPE
    SYNTAX INTEGER {
        normal(1),
        inverted(2),
        auto(3),
        up(4),
        down(5),
        orientation0(6),
        orientation90(7),
        orientation180(8),
        orientation270(9)
    }
   MAX-ACCESS read-write
   STATUS current
   DESCRIPTION
   "SGD for display orientation."
   ::= { zbrDisplay 22 }

--===========================
-- zebra.zbrPlatform.zbrPower
--===========================

zbrLowBatteryAlertAudio OBJECT-TYPE
    SYNTAX INTEGER (0..65535)
    MAX-ACCESS read-write
    STATUS current
    DESCRIPTION
    "Low Battery alert audio interval"
    ::= { zbrPowerLowBatteryAlert 1 }

zbrLowBatteryAlertText OBJECT-TYPE
    SYNTAX DisplayString (SIZE (0..100))
    MAX-ACCESS read-write
    STATUS current
    DESCRIPTION
    "Low Battery Alert Text"
    ::= { zbrPowerLowBatteryAlert 2 }

zbrPowerVoltage OBJECT-TYPE
    SYNTAX DisplayString (SIZE (0..20))
   MAX-ACCESS read-only
   STATUS current
   DESCRIPTION
   " The current battery voltage."
   ::= { zbrPower 5 }

zbrPowerPercentFull OBJECT-TYPE
   SYNTAX INTEGER (0..100)
   MAX-ACCESS read-only
   STATUS current
   DESCRIPTION
   " The battery status expressed as a percentage of the full battery charge."
   ::= { zbrPower 6 }

zbrPowerStatus OBJECT-TYPE
    SYNTAX INTEGER {
        ok(1),
        low(2)
    }
   MAX-ACCESS read-only
   STATUS current
   DESCRIPTION
   "The battery status."
   ::= { zbrPower 7 }

zbrpowerLowBatteryWarning OBJECT-TYPE
   SYNTAX DisplayString (SIZE (0..10))
   MAX-ACCESS read-only
   STATUS current
   DESCRIPTION
   "Current low-battery warning level - floating point number in volts from 0.0 to 9.95."
   ::= { zbrPower 8 }

zbrPowerLowBatteryWarningRaw OBJECT-TYPE
   SYNTAX INTEGER (0..255)
   MAX-ACCESS read-only
   STATUS current
   DESCRIPTION
   "Current low-battery warning level in hardwate A/D units."
   ::= { zbrPower 9 }

zbrPowerLowBatteryShutdown OBJECT-TYPE
   SYNTAX DisplayString (SIZE (0..10))
   MAX-ACCESS read-only
   STATUS current
   DESCRIPTION
   "The low battery shutdown level  - floating point number in volts from 0.0 to 9.95."
   ::= { zbrPower 12 }

zbrPowerLowBatteryTimeout OBJECT-TYPE
   SYNTAX INTEGER (0..65535)
   MAX-ACCESS read-write
   STATUS current
   DESCRIPTION
   "Low battery timeout. When the printer reaches the low battery state,
   the printer waits this number of seconds and then shuts down."
   ::= { zbrPower 13 }

zbrPowerInactivityTimeout OBJECT-TYPE
   SYNTAX INTEGER (0..65535)
   MAX-ACCESS read-write
   STATUS current
   DESCRIPTION
   "Inactivity timeout in seconds."
   ::= { zbrPower 14 }

zbrPowerCradleShutdownTimer OBJECT-TYPE
    SYNTAX INTEGER (0..65535)
    MAX-ACCESS read-write
    STATUS current
    DESCRIPTION
    "Cradle shutdown timer."
    ::= { zbrPower 15 }

zbrPowerLabelQueueShutdown OBJECT-TYPE
    SYNTAX INTEGER {
        yes(1),
        no(2)
    }
    MAX-ACCESS read-write
    STATUS current
    DESCRIPTION
    "Label Queue Shutdown."
    ::= { zbrPower 16 }

zbrPowerHealth OBJECT-TYPE
    SYNTAX INTEGER {
        good(1),
        replace(2),
        poor(3)
    }
   MAX-ACCESS read-only
   STATUS current
   DESCRIPTION
   "The health rating of the battery pack. Battery health can be  good, replace or poor."
   ::= { zbrPower 17 }

zbrPowerDtrPowerOff OBJECT-TYPE
    SYNTAX INTEGER {
        on(1),
        off(2)
    }
   MAX-ACCESS read-write
   STATUS current
   DESCRIPTION
   "When DTR is enabled the printer can be powered on and off via the DSR signal.
   When DTRpower off is enabled, a low to high transition will cause the printer to turn ON and a high to low transition
   will cause the printer to turn OFF. The printer will stay ON as long as DSR is high unless it reaches low
   battery shutdown or receives a command to shut down."
   ::= { zbrPower 18 }

zbrPowerShutdown OBJECT-TYPE
     SYNTAX INTEGER {
        off(2)
    }
   MAX-ACCESS read-write
   STATUS current
   DESCRIPTION
   "Setting this turn the printer off."
   ::= { zbrPower 19 }

zbrPowerPowerOnCycles OBJECT-TYPE
   SYNTAX INTEGER (0..999999)
   MAX-ACCESS read-only
   STATUS current
   DESCRIPTION
   "Number of power on cycles."
   ::= { zbrPower 20 }

zbrPowerDesignVoltage OBJECT-TYPE
   SYNTAX DisplayString (SIZE (0..10))
   MAX-ACCESS read-only
   STATUS current
   DESCRIPTION
   "Theoretical voltage of a new battery pack - floaing point number in volts."
   ::= { zbrPower 21 }

zbrPowerDesignCapacity OBJECT-TYPE
   SYNTAX INTEGER (0..99999)
   MAX-ACCESS read-only
   STATUS current
   DESCRIPTION
   "Theoretical capacity of a new battery pack in milliAmp-hours"
   ::= { zbrPower 22 }

zbrPowerManufactureDate OBJECT-TYPE
   SYNTAX DisplayString (SIZE (0..10))
   MAX-ACCESS read-only
   STATUS current
   DESCRIPTION
   "Date of manufacture."
   ::= { zbrPower 25 }

zbrPowerRelativeStateOfCharge OBJECT-TYPE
   SYNTAX INTEGER (0..100)
   MAX-ACCESS read-only
   STATUS current
   DESCRIPTION
   "State of charge as a percentage."
   ::= { zbrPower 26 }

zbrPowerSerialNumber OBJECT-TYPE
   SYNTAX DisplayString (SIZE (0..99))
   MAX-ACCESS read-only
   STATUS current
   DESCRIPTION
   "Printer serial number."
   ::= { zbrPower 27 }

zbrPowerCycleCount OBJECT-TYPE
   SYNTAX INTEGER (0..999999)
   MAX-ACCESS read-only
   STATUS current
   DESCRIPTION
   "Returns the number of charge cycles the battery pack has experienced. A cycle is defined as a discharge
of 80% of the pack's full charge capacity plus the concatenated partial charges that add to 80% of the
pack's full charge capacity."
   ::= { zbrPower 28 }

zbrPowerFullChargeCapacity OBJECT-TYPE
   SYNTAX INTEGER (0..99999)
   MAX-ACCESS read-only
   STATUS current
   DESCRIPTION
   "Full charge capacity in milliAmp-hours."
   ::= { zbrPower 29 }

zbrPowerDateFirstUsed OBJECT-TYPE
   SYNTAX DisplayString (SIZE (0..10))
   MAX-ACCESS read-only
   STATUS current
   DESCRIPTION
   "Returns the date the pack is charged for the first time."
   ::= { zbrPower 30 }

zbrPowerBatteryLowWarningStatus OBJECT-TYPE
   SYNTAX INTEGER {
      no(1),
      yes(2)
    }
    MAX-ACCESS read-only
    STATUS current
    DESCRIPTION
    "Battery Low Warning Status"
    ::= { zbrPower 31 }

zbrPowerBatteryReplaceCycleCountThreshold OBJECT-TYPE
   SYNTAX INTEGER (100..2450)
   MAX-ACCESS read-write
   STATUS current
   DESCRIPTION
   "Led Lights when Cycle Count Threshold is met or exceeded."
   ::= { zbrPower 32 }
   
zbrPowerBatteryReplaceCapacityRatioThreshold OBJECT-TYPE
   SYNTAX INTEGER (0..100)
   MAX-ACCESS read-write
   STATUS current
   DESCRIPTION
   "Led Lights when Capacity Ratio Threshold is met or exceeded."
   ::= { zbrPower 33 }
   
zbrPowerBatteryReplaceStateOfChargeThreshold OBJECT-TYPE
   SYNTAX INTEGER (0..100)
   MAX-ACCESS read-write
   STATUS current
   DESCRIPTION
   "Led Lights when State Of Charge Threshold is met or exceeded."
   ::= { zbrPower 34 }
   
zbrPowerBatteryLedBlinkRate OBJECT-TYPE
   SYNTAX INTEGER (0..127)
   MAX-ACCESS read-write
   STATUS current
   DESCRIPTION
   "Led Blink Rate."
   ::= { zbrPower 35 }
   
zbrPowerBatteryLedOnTime OBJECT-TYPE
   SYNTAX INTEGER (0..255)
   MAX-ACCESS read-write
   STATUS current
   DESCRIPTION
   "Led On Duration."
   ::= { zbrPower 36 }
   
zbrPowerBatteryLedOffTime OBJECT-TYPE
   SYNTAX INTEGER (0..255)
   MAX-ACCESS read-write
   STATUS current
   DESCRIPTION
   "Led Off Duration."
   ::= { zbrPower 37 }
   
zbrPowerBatteryLedEnable OBJECT-TYPE
   SYNTAX INTEGER {
      on(1),
      off(2),
      na(3)
   }
   MAX-ACCESS read-write
   STATUS current
   DESCRIPTION
   "Enable Led to blink when any one of the thresholds is reached."
   ::= { zbrPower 38 }

zbrPowerOverride OBJECT-TYPE
   SYNTAX INTEGER {
      auto(1),
      manual(2),
      na(3)
   }
   MAX-ACCESS read-only
   STATUS current
   DESCRIPTION
   "Auto or Manual power up. Auto ignores power button."
   ::= { zbrPower 39 }

zbrPowerPercentHealth OBJECT-TYPE
   SYNTAX INTEGER (0..100)
   MAX-ACCESS read-only
   STATUS current
   DESCRIPTION
   " The battery health expressed as a percentage of design capacity."
   ::= { zbrPower 40 }
   
zbrPowerAverageCurrent OBJECT-TYPE
   SYNTAX INTEGER (-32768..32767)
   MAX-ACCESS read-only
   STATUS current
   DESCRIPTION
   "Returns the signed average battery current in milliamps."
   ::= { zbrPower 41 }
   
zbrPowerCurrent OBJECT-TYPE
   SYNTAX INTEGER (-32768..32767)
   MAX-ACCESS read-only
   STATUS current
   DESCRIPTION
   "Returns the signed instantaneous battery current in milliamps."
   ::= { zbrPower 42 }
   
zbrPowerAverageTimeToEmpty OBJECT-TYPE
   SYNTAX INTEGER (0..65535)
   MAX-ACCESS read-only
   STATUS current
   DESCRIPTION
   "Returns the time to empty in minutes at the average current draw."
   ::= { zbrPower 43 }
   
zbrPowerAverageTimeToFull OBJECT-TYPE
   SYNTAX INTEGER (0..65535)
   MAX-ACCESS read-only
   STATUS current
   DESCRIPTION
   "Returns the time to full in minutes at the average charge current."
   ::= { zbrPower 44 }
   
zbrPowerRemainingCapacity OBJECT-TYPE
   SYNTAX INTEGER (0..65535)
   MAX-ACCESS read-only
   STATUS current
   DESCRIPTION
   "Remaining battery capacity in milliAmp-hours."
   ::= { zbrPower 45 }
   
zbrPowerAbsoluteStateOfCharge OBJECT-TYPE
   SYNTAX INTEGER (0..100)
   MAX-ACCESS read-only
   STATUS current
   DESCRIPTION
   " The remaining capacity expressed as a percentage of design capacity."
   ::= { zbrPower 46 }
      
zbrPowerPartNumber OBJECT-TYPE
   SYNTAX DisplayString (SIZE (0..12))
   MAX-ACCESS read-only
   STATUS current
   DESCRIPTION
   "Returns the Power Precision Battery Part Number."
   ::= { zbrPower 47 }

zbrPowerCellModelNumber OBJECT-TYPE
   SYNTAX DisplayString (SIZE (0..10))
   MAX-ACCESS read-only
   STATUS current
   DESCRIPTION
   "Returns the Power Precision Battery Cell Model Number."
   ::= { zbrPower 48 }

zbrPowerDecomTholdPerc OBJECT-TYPE
   SYNTAX INTEGER (0..100)
   MAX-ACCESS read-write
   STATUS current
   DESCRIPTION
   "Returns the Power Precision Battery Decommission Threshold Percentage."
   ::= { zbrPower 49 }

zbrPowerLifetimeTempLow OBJECT-TYPE
   SYNTAX INTEGER (-128..127)
   MAX-ACCESS read-only
   STATUS current
   DESCRIPTION
   "Returns the Power Precision Battery Lifetime Temperature Low."
   ::= { zbrPower 70 }

zbrPowerLifetimeTempHigh OBJECT-TYPE
   SYNTAX INTEGER (-128..127)
   MAX-ACCESS read-only
   STATUS current
   DESCRIPTION
   "Returns the Power Precision Battery Lifetime Temperature High."
   ::= { zbrPower 71 }
   
zbrPowerChgrStatus OBJECT-TYPE
   SYNTAX DisplayString (SIZE (0..150))
   MAX-ACCESS read-only
   STATUS current
   DESCRIPTION
   "Returns the Power Precision Battery Charger Status as a list of comma separated text."
   ::= { zbrPower 72 }
   
zbrPowerLearningRequired OBJECT-TYPE
   SYNTAX INTEGER {
      yes(1),
      no(2),
      na(3)
   }
   MAX-ACCESS read-only
   STATUS current
   DESCRIPTION
   "Returns a state denoting whether a learning cycle is required."
   ::= { zbrPower 73 }
   
zbrPowerTemperature OBJECT-TYPE
   SYNTAX DisplayString (SIZE (1..10))
   MAX-ACCESS read-only
   STATUS current
   DESCRIPTION
   "Returns the current battery temperature in degrees C."
   ::= { zbrPower 74 }

zbrPowerHoldCurrent OBJECT-TYPE
   SYNTAX INTEGER {
      on(1),
      off(2)
    }
    MAX-ACCESS read-write
    STATUS current
    DESCRIPTION
    "Extended motor hold enable"
    ::= { zbrPower 75 }

zbrPowerWakeRadio OBJECT-TYPE
   SYNTAX INTEGER {
      on(1),
      off(2)
   }
   MAX-ACCESS read-write
   STATUS current
   DESCRIPTION
   "Allows the printer awaken upon data receiption over WiFi & BT."
   ::= { zbrPower 76 }

zbrPowerBatteryType OBJECT-TYPE
    SYNTAX INTEGER {
        battery(1),
        none(2),
        sb(3),
        ppp(4),
        be(5)
    }
   MAX-ACCESS read-only
   STATUS current
   DESCRIPTION
   "The battery pack type.
   Battery types - battery, none (no battery installed), sb (smart battery), ppp (power precision plus), be (battery eliminator)."
   ::= { zbrPower 77 }

--==================================
-- zebra.zbrPlatform.zbrPower.zbrSleep
--==================================
zbrSleepEnable OBJECT-TYPE
   SYNTAX INTEGER {
        on(1),
        off(2)
    }
    MAX-ACCESS read-write
    STATUS current
    DESCRIPTION
    "Sleep mode enable"
    ::= { zbrSleep 1 }
    
zbrSleepTimeout OBJECT-TYPE
    SYNTAX INTEGER (0..65535)
    MAX-ACCESS read-write
    STATUS current
    DESCRIPTION
    "Sleep timeout in seconds."
    ::= { zbrSleep 2 }

zbrSleepNow OBJECT-TYPE
    SYNTAX DisplayString (SIZE (0..5))
    MAX-ACCESS read-write
    STATUS current
    DESCRIPTION
    "Put the printer to sleep as soon as it has been idle for at least 1 second."
    ::= { zbrSleep 3 }

zbrSleepCradle OBJECT-TYPE
  SYNTAX INTEGER {
      enabled(1),
      disabled(2)
    }
   MAX-ACCESS read-write
   STATUS current
   DESCRIPTION
   "Select whether sleep is disabled or enabled when printer is in cradle."
   ::= { zbrSleep 4 }

zbrSleepUnassociated OBJECT-TYPE
   SYNTAX INTEGER {
      on(1),
      off(2)
   }
   MAX-ACCESS read-write
   STATUS current
   DESCRIPTION
   "Allows the printer to sleep when unassociated."
   ::= { zbrSleep 5 }
   
--=========================================
-- zebra.zbrPlatform.zbrPower.zbrEnergyStar
--=========================================

zbrEnergyStarEnable OBJECT-TYPE
   SYNTAX INTEGER {
        on(1),
        off(2)
    }
   MAX-ACCESS read-write
   STATUS current
   DESCRIPTION
   "Enable or disable Energy Star."
   ::= { zbrEnergyStar 1 }

zbrEnergyStarTimeout OBJECT-TYPE
    SYNTAX INTEGER (0..65535)
    MAX-ACCESS read-write
    STATUS current
    DESCRIPTION
    "Energy Star timeout in seconds."
    ::= { zbrEnergyStar 2 }
        
--==================================
-- zebra.zbrPlatform.zbrPdl.zbrCpcl
--==================================

zbrCpclSynchronousMode OBJECT-TYPE
   SYNTAX INTEGER {
        on(1),
        off(2)
    }
    MAX-ACCESS read-write
    STATUS current
    DESCRIPTION
    "Device CPCL Synchronous Mode"
    ::= { zbrCpcl 1 }

zbrCpclPrintTwoKey OBJECT-TYPE
    SYNTAX DisplayString (SIZE (0..10))
    MAX-ACCESS read-write
    STATUS current
    DESCRIPTION
    "Print Two Key Report"
    ::= { zbrCpcl 2 }

zbrCpclFeedSkip OBJECT-TYPE
    SYNTAX INTEGER (0..50)
    MAX-ACCESS read-write
    STATUS current
    DESCRIPTION
    "Set the printer's feed skip length [0 to 50].  Controls the length of paper, expressed in dots,
    that the printer advances after the trailing edge of a media synchronization mark (a bar or a gap) before the current label ends."
    ::= { zbrCpcl 3 }

zbrCpclFeedLength OBJECT-TYPE
    SYNTAX INTEGER (0..20000)
    MAX-ACCESS read-write
    STATUS current
    DESCRIPTION
    "Set the printer's feed length [0 to 20000].  Controls the length of paper, expressed in dots,
    that the printer advances looking for the starting edge of a media synchronization mark (a bar or a gap)."
    ::= { zbrCpcl 4 }

--==================================
-- zebra.zbrPlatform.zbrPdl.zbrZpl
--==================================

zbrZplFormatCommandPrefix OBJECT-TYPE
    SYNTAX DisplayString (SIZE (0..10))
    MAX-ACCESS read-write
    STATUS current
    DESCRIPTION
    "ZPL Format Character Prefix"
    ::= { zbrZpl 1 }

zbrZplControlCommandPrefix OBJECT-TYPE
    SYNTAX DisplayString (SIZE (0..10))
    MAX-ACCESS read-write
    STATUS current
    DESCRIPTION
    "ZPL Control Character Prefix"
    ::= { zbrZpl 2 }

zbrZplDelimiterCharacter OBJECT-TYPE
    SYNTAX DisplayString (SIZE (0..10))
    MAX-ACCESS read-write
    STATUS current
    DESCRIPTION
    "ZPL Delimiter Character"
    ::= { zbrZpl 3 }

zbrZplLeftPosition OBJECT-TYPE
    SYNTAX INTEGER (-9999..9999)
    MAX-ACCESS read-write
    STATUS current
    DESCRIPTION
    "SGD to set a label's left margin offset"
    ::= { zbrZpl 4 }

zbrZplZplMode OBJECT-TYPE
    SYNTAX INTEGER {
       zpl-II(1),
       zpl(2)
    }
    MAX-ACCESS read-write
    STATUS current
    DESCRIPTION
    "SGD to set the zpl_mode to [zpl II,zpl]"
    ::= { zbrZpl 5 }

zbrZplSystemStatus OBJECT-TYPE
    SYNTAX DisplayString (SIZE (0..50))
    MAX-ACCESS read-only
    STATUS current
    DESCRIPTION
    "Returns the system error and warning status in the form of a ~HQ response"
    ::= { zbrZpl 6 }

zbrZplSystemError OBJECT-TYPE
    SYNTAX DisplayString (SIZE (0..50))
    MAX-ACCESS read-only
    STATUS current
    DESCRIPTION
    " Returns the system error status in the form of a ~HQ response"
    ::= { zbrZpl 7 }

zbrZplNoErrorsBootDone OBJECT-TYPE
    SYNTAX DisplayString (SIZE (0..10))
    MAX-ACCESS read-only
    STATUS current
    DESCRIPTION
    " Returns yes if the printer is fully booted and system error status is zero"
    ::= { zbrZpl 8 }

zbrZplPrintOrientation OBJECT-TYPE
    SYNTAX DisplayString (SIZE (0..10))
    MAX-ACCESS read-write
    STATUS current
    DESCRIPTION
    "SGD to set label orientation"
    ::= { zbrZpl 9 }

zbrZplLabelTop OBJECT-TYPE
    SYNTAX INTEGER (-240..240)
    MAX-ACCESS read-write
    STATUS current
    DESCRIPTION
    "SGD to set a label's top offset"
    ::= { zbrZpl 10 }

zbrZplPrintReport OBJECT-TYPE
    SYNTAX DisplayString (SIZE (0..20))
    MAX-ACCESS read-write
    STATUS current
    DESCRIPTION
    "Print the desired report on a label and choices are- settings,network,formats,images,fonts,barcodes,all,sensor profile"
    ::= { zbrZpl 11 }
    
zbrZplRelativeDarkness OBJECT-TYPE
   SYNTAX INTEGER (-300..300)
   MAX-ACCESS read-write
   STATUS current
   DESCRIPTION
   "The printer relative darkness."
   ::= { zbrZpl 12 }

zbrZplLabelLengthAlways OBJECT-TYPE
   SYNTAX INTEGER {
      no(1),
      yes(2)
    }
    MAX-ACCESS read-write
    STATUS current
    DESCRIPTION
    "Apply label length defined by ^LL when the media is Gap or Black Mark"
    ::= { zbrZpl 13 }

zbrZplLabelLength OBJECT-TYPE
   SYNTAX INTEGER (1..32000)
   MAX-ACCESS read-write
   STATUS current
   DESCRIPTION
   "Length of a label."
   ::= { zbrZpl 14 }
    
--==================================
-- zebra.zbrPlatform.zbrPdl.zbrEzpl
--==================================
zbrEzplPrintMethod OBJECT-TYPE
   SYNTAX INTEGER {
       thermal-transfer(1),
       direct-thermal(2)
    }
    MAX-ACCESS read-write
    STATUS current
    DESCRIPTION
    "SGD to retrieve and set the print method to thermal transfer or direct thermal"
    ::= { zbrEzpl 1 }

zbrEzplPrintMode OBJECT-TYPE
   SYNTAX INTEGER {
        tear-off(1),
        peel-off(2),
        rewind(3),
        cutter(4),
        delayed-cut(5),
        linerless-peel(6),
        linerless-rewind(7),
        linerless-tear(8),
        applicator(9),
        linerless-cut(10),
        linerless-delay-cut(11),
        partial-cut(12),
        partial-delay-cut(13),
        stream(14)
   }
   MAX-ACCESS read-write
   STATUS current
   DESCRIPTION
   "Set the print mode to [tear off,peel off,rewind,cutter,delayed cut,linerless peel,linerless rewind,linerless tear,applicator,linerless cut,linerless delay cut,partial cut,partial delay cut,stream]"
   ::= { zbrEzpl 2 }
   
zbrEzplReprintMode OBJECT-TYPE
   SYNTAX INTEGER {
       on(1),
       off(2)
    }
    MAX-ACCESS read-write
    STATUS current
    DESCRIPTION
    "SGD to set the reprint mode to [on,off]"
    ::= { zbrEzpl 3 }

zbrEzplTearOff OBJECT-TYPE
    SYNTAX INTEGER (-120..120)
    MAX-ACCESS read-write
    STATUS current
    DESCRIPTION
    "SGD to set the tear off position [-120 to 120]"
    ::= { zbrEzpl 4 }

zbrEzplHeadCloseAction OBJECT-TYPE
   SYNTAX INTEGER {
        calibrate(1),
        feed(2),
        length(3),
        no-motion(4),
        short-cal(5),
        quick-cal(6)
    }
    MAX-ACCESS read-write
    STATUS current
    DESCRIPTION
    "The action to perform on head close"
    ::= { zbrEzpl 5 }

zbrEzplPowerUpAction OBJECT-TYPE
   SYNTAX INTEGER {
        calibrate(1),
        feed(2),
        length(3),
        no-motion(4),
        short-cal(5),
        quick-cal(6)
   }
   MAX-ACCESS read-write
   STATUS current
   DESCRIPTION
    "The action to perform on power up."
   ::= { zbrEzpl 6 }

zbrEzplLabelLengthMax OBJECT-TYPE
   SYNTAX INTEGER (1..39)
   MAX-ACCESS read-write
   STATUS current
   DESCRIPTION
   "SGD to set the label length in inches [1.0 to 39.0]"
   ::= { zbrEzpl 7 }

zbrEzplManualCalibration OBJECT-TYPE
   SYNTAX DisplayString (SIZE (0..100))
   MAX-ACCESS read-write
   STATUS current
   DESCRIPTION
   "SGD to initiate a manual calibration sequence"
   ::= { zbrEzpl 8 }

zbrEzplLabelSensor OBJECT-TYPE
   SYNTAX INTEGER (0..255)
   MAX-ACCESS read-write
   STATUS current
   DESCRIPTION
   "SGD to set paper out threshold values [0 to 255]"
   ::= { zbrEzpl 9 }

zbrEzplTakeLabel OBJECT-TYPE
   SYNTAX INTEGER (0..255)
   MAX-ACCESS read-write
   STATUS current
   DESCRIPTION
   "SGD to set the take label position [0 to 255]"
   ::= { zbrEzpl 10 }


zbrEzplRestoreDefaults OBJECT-TYPE
   SYNTAX INTEGER {
        none(1),
        restore-printer(2),
        restore-network(3)
    }
   MAX-ACCESS read-write
   STATUS current
   DESCRIPTION
    "Restore printer or network settings to defaults"
    ::= { zbrEzpl 12 }

zbrEzplEplLegacyMode OBJECT-TYPE
    SYNTAX DisplayString (SIZE (0..64))
    MAX-ACCESS read-write
    STATUS current
    DESCRIPTION
    "Configure printer to mimic EPL legacy printers"
    ::= { zbrEzpl 13 }

zbrEzplMediaType OBJECT-TYPE
   SYNTAX INTEGER {
        continuous(1),
        gap-notch(2),
        mark(3),
        auto-detect(4)
   }
   MAX-ACCESS read-write
   STATUS current
   DESCRIPTION
    "The media type to use and calibrate for."
   ::= { zbrEzpl 14 }
   
zbrEzplTakeLabelCalibration OBJECT-TYPE
   SYNTAX INTEGER {
        starting(1),
        inProgress(2),
        complete(3)
   }
   MAX-ACCESS read-write
   STATUS current
   DESCRIPTION
    "SGD to initiate a label taken sensor calibration sequence."
   ::= { zbrEzpl 15 }
   
--===========================
-- zebra.zbrPlatform
--===========================

zbrPlatformConnectionDownloadTimeout OBJECT-TYPE
    SYNTAX INTEGER (0..65535)
    MAX-ACCESS read-write
    STATUS current
    DESCRIPTION
    "If greater than 0, the printer will abort a firmware download if the printer
     fails to receive any download data in the set amount of seconds. If the set amount of seconds is
     exceeded, the download will be aborted, and the printer automatically restarts. This command
     prevents the printer from being locked into the downloading state, if the communication to the
     host is interrupted."
    ::= { zbrPlatform 20 }

zbrPlatformFirmwareDownloadInteractiveMode OBJECT-TYPE
   SYNTAX INTEGER {
        on(1),
        off(2)
    }
   MAX-ACCESS read-write
   STATUS current
   DESCRIPTION
   "Enable/disable firmware download interactive mode. When enabled, printer will send back 
    status messages to the host as the firmware file is being sent and processed. 
    This allows the host to see the progress of the download in real-time."
   ::= { zbrPlatform 21 }
   
--===========================
-- zebra.zbrOptions.zbrOdometer
--===========================

zbrOdometerMediaMarkerCount1 OBJECT-TYPE
    SYNTAX Unsigned32
    MAX-ACCESS read-write
    STATUS current
    DESCRIPTION
    "The first (count1) user resettable counter.
    The user resettable counters track how much media has passed through the printer in centimeters.
    To reset the counter, set it to 0."
    ::= { zbrOdometer 1 }

zbrOdometerMediaMarkerCount2 OBJECT-TYPE
    SYNTAX Unsigned32
    MAX-ACCESS read-write
    STATUS current
    DESCRIPTION
    "The second (count2) user resettable counter.
    The user resettable counters track how much media has passed through the printer in centimeters.
    To reset the counter, set it to 0."
    ::= { zbrOdometer 2 }

zbrOdometerHeadClean OBJECT-TYPE
    SYNTAX Unsigned32
    MAX-ACCESS read-write
    STATUS current
    DESCRIPTION
    "Head Clean odometer count.  This counter tracks
    how many centimeters have passed through the printer since the head was last cleaned.
    To reset the counter, set it to 0."
    ::= { zbrOdometer 3 }

zbrOdometerHeadNew OBJECT-TYPE
    SYNTAX Unsigned32
    MAX-ACCESS read-write
    STATUS current
    DESCRIPTION
    "Head New odometer count.  This counter tracks
    how many centimeters have passed through the printer since the head was last replaced.
    To reset the counter, set it to 0."
    ::= { zbrOdometer 4 }

zbrOdometerUserLabelCount OBJECT-TYPE
   SYNTAX Unsigned32
   MAX-ACCESS read-write
   STATUS current
   DESCRIPTION
   "The user label counter keeps track of how many labels have been printed
   since the last re-set of the counter. The user's label count can be set to an initial value
   and incremented every time a label is printed."
   ::= { zbrOdometer 6 }

zbrOdometerTotalLabelCount OBJECT-TYPE
   SYNTAX Unsigned32
   MAX-ACCESS read-only
   STATUS current
   DESCRIPTION
   "The total number of labels that printed over the life of the printer."
   ::= { zbrOdometer 7 }

zbrOdometerTotalPrintLength OBJECT-TYPE
   SYNTAX Unsigned32
   MAX-ACCESS read-only
   STATUS current
   DESCRIPTION
   "The total length of media that printed over the life of the printer."
   ::= { zbrOdometer 8 }

zbrOdometerLatchOpenCount OBJECT-TYPE
   SYNTAX Unsigned32
   MAX-ACCESS read-write
   STATUS current
   DESCRIPTION
   "The number of times the printer's latch has been opened. The latch open count
   can be set to an initial value and incremented every time the latch is opened. Typically the latch is opened
   each time a roll of media is loaded."
   ::= { zbrOdometer 9 }

zbrOdometerLabelDotLength OBJECT-TYPE
   SYNTAX Unsigned32
   MAX-ACCESS read-only
   STATUS current
   DESCRIPTION
   "Length of the last label printed or fed (in dots)."
   ::= { zbrOdometer 10 }

zbrOdometerMediaMarkerCount OBJECT-TYPE
    SYNTAX Unsigned32
    MAX-ACCESS read-write
    STATUS current
    DESCRIPTION
    "The media marker counter keeps track of
    how many labels have passed through the printer, (wether or not they have been printed) by
    counting the bar sense marks on the back of the media and the gap in gap media.
    To reset the counter, set it to 0."
    ::= { zbrOdometer 11 }

zbrOdometerUserLabelCount1 OBJECT-TYPE
   SYNTAX Unsigned32
   MAX-ACCESS read-write
   STATUS current
   DESCRIPTION
   "This parameter refers to the user label count number 1. The user
   label counter keeps track of how many labels have been printed since the last re-set of the counter."
   ::= { zbrOdometer 12 }

zbrOdometerUserLabelCount2 OBJECT-TYPE
   SYNTAX Unsigned32
   MAX-ACCESS read-write
   STATUS current
   DESCRIPTION
   "This parameter refers to the user label count number 2. The user
   label counter keeps track of how many labels have been printed since the last re-set of the counter."
   ::= { zbrOdometer 13 }

zbrOdometerRfidValidResettable OBJECT-TYPE
   SYNTAX Unsigned32
   MAX-ACCESS read-write
   STATUS current
   DESCRIPTION
   "This parameter refers to the RFID valid counter."
   ::= { zbrOdometer 14 }

zbrOdometerRfidVoidResettable OBJECT-TYPE
   SYNTAX Unsigned32
   MAX-ACCESS read-write
   STATUS current
   DESCRIPTION
   "This parameter refers to the RFID void counter."
   ::= { zbrOdometer 15 }

zbrOdometerTotalCuts OBJECT-TYPE
   SYNTAX Unsigned32
   MAX-ACCESS read-only
   STATUS current
   DESCRIPTION
   "This parameter refers to the non-resettable total cut counter (this contains the lower 32 bits)."
   ::= { zbrOdometer 16 }

zbrOdometerUserTotalCuts OBJECT-TYPE
   SYNTAX Unsigned32
   MAX-ACCESS read-write
   STATUS current
   DESCRIPTION
   "This parameter refers to the resettable cut counter. To reset the counter, set it to 0."
   ::= { zbrOdometer 17 }

zbrOdometerNetRibbonUse OBJECT-TYPE
   SYNTAX Unsigned32
   MAX-ACCESS read-only
   STATUS current
   DESCRIPTION
   "The total net length of ribbon that has moved through the printer (this contains the lower 32 bits), 
    with backup movement properly compensated for in the count."
   ::= { zbrOdometer 18 }
      
zbrOdometerNetMediaUse OBJECT-TYPE
   SYNTAX Unsigned32
   MAX-ACCESS read-only
   STATUS current
   DESCRIPTION
   "The total net length of media that has moved through the printer (this contains the lower 32 bits), 
    with backup movement properly compensated for in the count."
   ::= { zbrOdometer 19 }
   
--===========================
-- zebra.zbrOptions.zbrRtc
--===========================

zbrRtcTime OBJECT-TYPE
   SYNTAX DisplayString (SIZE (0..100))
   MAX-ACCESS read-write
   STATUS current
   DESCRIPTION
   "Current Real Time Clock time of day. Format is hh mm ss, seperated by colons."
   ::= { zbrRtc 1 }

zbrRtcDate OBJECT-TYPE
   SYNTAX DisplayString (SIZE (0..100))
   MAX-ACCESS read-write
   STATUS current
   DESCRIPTION
   "Current Real Time Clock date. Format is mm-dd-yy."
   ::= { zbrRtc 2 }

zbrRtcSetAlarm OBJECT-TYPE
   SYNTAX DisplayString (SIZE (0..100))
   MAX-ACCESS read-write
   STATUS current
   DESCRIPTION
   "Real Time Clock alarm setting."
   ::= { zbrRtc 3 }

zbrRtcEnableAlarm OBJECT-TYPE
   SYNTAX INTEGER {
        on(1),
        off(2)
    }
   MAX-ACCESS read-write
   STATUS current
   DESCRIPTION
   "Enable Real Time Clock alarm."
   ::= { zbrRtc 4 }

zbrRtcSetCounter OBJECT-TYPE
   SYNTAX INTEGER
   MAX-ACCESS read-write
   STATUS current
   DESCRIPTION
   "Real Time Clock counter."
   ::= { zbrRtc 5 }

zbrRtcEnableCounter OBJECT-TYPE
   SYNTAX INTEGER {
        on(1),
        off(2)
    }
   MAX-ACCESS read-write
   STATUS current
   DESCRIPTION
   "Enable Real Time Clock counter."
   ::= { zbrRtc 6 }

zbrRtcExists OBJECT-TYPE
   SYNTAX INTEGER {
        yes(1),
        no(2)
    }
    MAX-ACCESS read-only
    STATUS current
    DESCRIPTION
    "RTC exists"
    ::= { zbrRtc 7 }

zbrRtcTimezone OBJECT-TYPE
   SYNTAX DisplayString (SIZE (0..128))
   MAX-ACCESS read-write
   STATUS current
   DESCRIPTION
   " The fully specified TZ POSIX string.  This includes the timezone character specifier, offset from UTC, 
    and daylight saving time adjustment and when to go on and off of daylight savings time if that pertains to this timezone.
    example: use EST5EDT4,M3.2.0/02:00:00,M11.1.0/02:00:00 if you live in the eastern timezone in the United States of America."
   ::= { zbrRtc 8 }

zbrRtcUnixTimestamp OBJECT-TYPE
   SYNTAX DisplayString (SIZE (0..12))
   MAX-ACCESS read-write
   STATUS current
   DESCRIPTION
   "Number of seconds since Unix Epoch"
   ::= { zbrRtc 9 }
--===========================
-- zebra.zbrOptions
--===========================
zbrOptionsCutter OBJECT-TYPE
   SYNTAX INTEGER {
      no(1),
      yes(2)
    }
    MAX-ACCESS read-only
    STATUS current
    DESCRIPTION
    "Cutter Option Installed"
    ::= { zbrOptions 3 }

zbrOptionsRewind OBJECT-TYPE
   SYNTAX  INTEGER {
       no(1),
       yes(2)
    }
    MAX-ACCESS read-only
    STATUS current
    DESCRIPTION
    "Rewind Option Installed"
    ::= { zbrOptions 4 }

zbrOptionsLinerTakeup OBJECT-TYPE
   SYNTAX INTEGER {
      no(1),
      yes(2)
    }
    MAX-ACCESS read-only
    STATUS current
    DESCRIPTION
    "Liner Takeup Option Installed"
    ::= { zbrOptions 5 }

zbrOptionsValuePeelRewind OBJECT-TYPE
    SYNTAX   INTEGER {
      no(1),
      yes(2)
    }
    MAX-ACCESS   read-only
    STATUS   current
    DESCRIPTION
    "Value Peel Option Installed"
    ::= { zbrOptions 6 }

zbrOptionsPeel OBJECT-TYPE
   SYNTAX  INTEGER {
      no(1),
      yes(2)
    }
    MAX-ACCESS read-only
    STATUS current
    DESCRIPTION
    "Peel Option Installed"
    ::= { zbrOptions 7 }

zbrOptionsApplicator OBJECT-TYPE
   SYNTAX  INTEGER {
      no(1),
      yes(2)
    }
   MAX-ACCESS read-only
    STATUS current
    DESCRIPTION
    "Applicator Installed"
    ::= { zbrOptions 8 }

zbrOptionsVerifier OBJECT-TYPE
    SYNTAX  INTEGER {
      no(1),
      yes(2)
    }
    MAX-ACCESS read-only
    STATUS current
    DESCRIPTION
    "Verifier Installed"
    ::= { zbrOptions 9 }

zbrOptionsSensorPeelerEngaged OBJECT-TYPE
    SYNTAX DisplayString (SIZE (0..20))
    MAX-ACCESS read-write
    STATUS current
    DESCRIPTION
    "Sensor Peeler Engaged"
    ::= { zbrOptions 20 }

--=================================================================================================
--clean_cutter deprecated as of EPOCH_RELOADED (Benz, Sentinel, Evo6ULL, ..etc..) and going forward 
--(Oct. 2019)
--=================================================================================================
--zbrOptionsCleanCutterMode OBJECT-TYPE
--   SYNTAX INTEGER {
--       on(1),
--       off(2)
--    }
--    MAX-ACCESS read-write
--    STATUS current
--    DESCRIPTION
--    "mediaControl.clean_cutter:intBufToOn1Off2String,notOn1is2StringToIntBuf:Turn on/off clean cutter mode"
--    ::= { zbrOptions 25 }

--=================================================================================================
--zebra.zbrOptions.zbrOptUnsolictedAlerts
--=================================================================================================

zbrOptUnsAlertsNumEntries OBJECT-TYPE
    SYNTAX  INTEGER
    MAX-ACCESS read-only
    STATUS current
    DESCRIPTION
    "Some fixed number of entries."
    ::= { zbrOptUnsolictedAlerts 1 }

zbrOptUnsAlertsTable OBJECT-TYPE
    SYNTAX  SEQUENCE OF ZbrOptUnsAlertsEntry
    MAX-ACCESS  not-accessible
    STATUS  current
    DESCRIPTION
    "Table of configured alerts.

      The number of entries is given by the value of zbrOptUnsAlertsNumEntries."
    ::= { zbrOptUnsolictedAlerts 2 }

zbrOptUnsAlertsEntry OBJECT-TYPE
    SYNTAX  ZbrOptUnsAlertsEntry
    MAX-ACCESS  not-accessible
    STATUS  current
    DESCRIPTION
    "One entry in the configured alerts table."
    INDEX   { zbrOptUnsAlertsIndex }
    ::= { zbrOptUnsAlertsTable 1 }

ZbrOptUnsAlertsEntry ::=
    SEQUENCE {
        zbrOptUnsAlertsIndex
            INTEGER,
        zbrOptUnsAlertsCondition
            INTEGER,
        zbrOptUnsAlertsDestination
            INTEGER,
        zbrOptUnsAlertsTrigger
            INTEGER,
        zbrOptUnsAlertsAddress
            DisplayString,
        zbrOptUnsAlertsPort
            INTEGER,
        zbrOptUnsAlertsQuelling
            INTEGER,
        zbrOptUnsAlertsSgdName
            DisplayString
    }

zbrOptUnsAlertsIndex OBJECT-TYPE
    SYNTAX  INTEGER (0..2147483647)
    MAX-ACCESS  read-only
    STATUS  current
    DESCRIPTION
    "Table row number"
    ::= { zbrOptUnsAlertsEntry 1 }

zbrOptUnsAlertsCondition OBJECT-TYPE
    SYNTAX  INTEGER {
       none(1),
       paper-out(2),
       ribbon-out(3),
       head-too-hot(4),
       head-cold(5),
       head-open(6),
       power-supply-over-temp(7),
       ribbon-in(8),
       rewind(9),
       cutter-jammed(10),
       printer-paused(11),
       pq-job-completed(12),
       label-ready(13),
       head-element-bad(14),
       basic-runtime(15),
       basic-forced(16),
       power-on(17),
       clean-printhead(18),
       media-low(19),
       ribbon-low(20),
       replace-head(21),
       battery-low(22),
       rfid-error(23),
       all-messages(24),
       cold-start(25),
       sgd-changed(26),
       motor-over-temp(27),
       head-shutdown(28),
       power-off(29),
       power-reset(30),
       no-rfid-reader(31),
       thermistor-fault(32),
       invalid-head(33),
       rfid-country-code-error(34),
       pmcu-download-fail(36),
       ribbon-auth-error(37),
       country-code-not-selected(39),
       battery-missing(40),
       media-catridge(41),
       media-cartridge-load-error(42),
       media-cartridge-eject-error(43),
       media-cartridge-forced-eject(44),
       cleaning-mode-init(45),
       csr-avail(46),
       ribbon-tension-system-error(47),
       cover-open(48),
       clean-cutter(49),
       paper-error(50),
       duplicate-ip(51)
    }    
    MAX-ACCESS  read-only
    STATUS  current
    DESCRIPTION
    "Condition to trigger the alert."
    ::= { zbrOptUnsAlertsEntry 2 }

zbrOptUnsAlertsDestination OBJECT-TYPE
    SYNTAX  INTEGER {
       serial(1),
       parallel(2),
       e-mail(3),
       tcp(4),
       udp(5),
       snmp(6),
       usb(7),
       http-post(8),
       bluetooth(9),
       sdk(10),
       mqtt(11),
       all-destinations(99)
    }
    MAX-ACCESS  read-only
    STATUS  current
    DESCRIPTION
    "Destination of the alert message."
    ::= { zbrOptUnsAlertsEntry 3 }

zbrOptUnsAlertsTrigger OBJECT-TYPE
   SYNTAX INTEGER {
      off(1),
      on-set-only(2),
      on-clear-only(3),
      on-both-set-and-clear(4)
    }
    MAX-ACCESS  read-only
    STATUS  current
    DESCRIPTION
    "Send this message when the condition occurs."
    ::= { zbrOptUnsAlertsEntry 4 }

zbrOptUnsAlertsAddress OBJECT-TYPE
    SYNTAX DisplayString (SIZE (0..64))
    MAX-ACCESS read-only
    STATUS current
    DESCRIPTION
    "Destination specific address to send the message to."
    ::= { zbrOptUnsAlertsEntry 6 }

zbrOptUnsAlertsPort OBJECT-TYPE
    SYNTAX  INTEGER
    MAX-ACCESS  read-only
    STATUS  current
    DESCRIPTION
    "Destination specific port number to send the message to."
    ::= { zbrOptUnsAlertsEntry 7 }

zbrOptUnsAlertsQuelling OBJECT-TYPE
   SYNTAX INTEGER {
      no(1),
      yes(2)
    }
    MAX-ACCESS  read-only
    STATUS  current
    DESCRIPTION
    "Enable or disable this alert."
    ::= { zbrOptUnsAlertsEntry 8 }
zbrOptUnsAlertsSgdName OBJECT-TYPE
    SYNTAX DisplayString (SIZE (0..64))
    MAX-ACCESS read-only
    STATUS current
    DESCRIPTION
    "SGD name specific to this alert."
    ::= { zbrOptUnsAlertsEntry 9 }

zbrOptUnsAlertsAddEntry OBJECT-TYPE
    SYNTAX DisplayString (SIZE (0..255))
    MAX-ACCESS read-write
    STATUS current
    DESCRIPTION
    "String of comma delimited fields used to setup an alert.
    format: <condition>,<destination>,<send on SET condition>,<send on CLEAR condition>,<destination address>,<destination port>,<quelling>,<sgd name for SGD SET conditions>
    where:
    <condition> is the text of one of the conditions in zbrOptUnsAlertsConditions
    <destination> is  the text of one of the destinations in zbrOptUnsAlertsDestination
    <send on SET condition> is 'Y' or 'N' depending on if you want to see an alert when the condition occurs
    <send on CLEAR condition> is 'Y' or 'N' depending on if you want to see an alert when the condition is cleared
    <destination address> is the address to send the alert to (applicable to some destinations, leave empty for other destinations)
    <destination port> is the destination port to send the alert to (applicable to some destinations, 0 for other destinations)
    <quelling> is 'Y' or 'N' depending on if you want to quell the alert
    <sgd name for SGD SET conditions> is the sgd name for which you want an alert when an SGD is set

    examples values:
    COLD START,SNMP,Y,N,255.255.255.255,162,N,
    HEAD OPEN,USB,N,Y,,0,N,
    SGD SET,UDP,Y,N,172.30.16.10,9100,N,alerts.configured

    NOTES:
    To remove an alert <SET> and <CLEAR> set both to 'N' with all other information matching alert to remove.
    This OID will always return an empty value when read."
    ::= { zbrOptUnsolictedAlerts 3 }
    
zbrOptUnsAlertsConditions OBJECT-TYPE
    SYNTAX OCTET STRING (SIZE (0..1024))
    MAX-ACCESS read-only
    STATUS current
    DESCRIPTION
    "A list of all the conditions that can be used in zbrOptUnsAlertsAddEntry"
    ::= { zbrOptUnsolictedAlerts 4 }
    
zbrOptUnsAlertsDestinations OBJECT-TYPE
    SYNTAX DisplayString (SIZE (0..255))
    MAX-ACCESS read-only
    STATUS current
    DESCRIPTION
    "A list of all the destinations that can be used in zbrOptUnsAlertsAddEntry"
    ::= { zbrOptUnsolictedAlerts 5 }

zbrOptUnsAlertsSendCurrentStatusAlerts OBJECT-TYPE
    SYNTAX DisplayString (SIZE (0..255))
    MAX-ACCESS read-write
    STATUS current
    DESCRIPTION
    "For the specified destination generate all configured alerts for current status conditions in the printer."
    ::= { zbrOptUnsolictedAlerts 6 }

--=================================================================================================
--zebra.zbrOptions.zbrOptUnsolictedAlerts.zbrOptUnsAlrtTrackedSettings
--=================================================================================================
zbrOptUnsAlrtTrackLogTrackedSettings OBJECT-TYPE
    SYNTAX OCTET STRING (SIZE (0..10000))
    MAX-ACCESS read-write
    STATUS current
    DESCRIPTION
    "A ',' delimited list of SGDs for which sets should be logged"
    ::= { zbrOptUnsAlrtTrackedSettings 1 }

zbrOptUnsAlrtTrackLogNumEntries OBJECT-TYPE
    SYNTAX  INTEGER
    MAX-ACCESS read-only
    STATUS current
    DESCRIPTION
    "Number of entries in the log."
    ::= { zbrOptUnsAlrtTrackedSettings 2 }

zbrOptUnsAlrtTrackLogTable OBJECT-TYPE
    SYNTAX  SEQUENCE OF ZbrOptUnsAlrtTrackLogEntry
    MAX-ACCESS  not-accessible
    STATUS  current
    DESCRIPTION
    "Table of log entries.

      The number of entries is given by the value of zbrOptUnsAlrtTrackLogNumEntries."
    ::= { zbrOptUnsAlrtTrackedSettings 3 }

zbrOptUnsAlrtTrackLogEntry OBJECT-TYPE
    SYNTAX  ZbrOptUnsAlrtTrackLogEntry
    MAX-ACCESS  not-accessible
    STATUS  current
    DESCRIPTION
    "One entry in the tracked log table."
    INDEX   { zbrOptUnsAlrtTrackLogIndex }
    ::= { zbrOptUnsAlrtTrackLogTable 1 }

ZbrOptUnsAlrtTrackLogEntry ::=
    SEQUENCE {
        zbrOptUnsAlrtTrackLogIndex
            INTEGER,
        zbrOptUnsAlrtTrackLogValue
            DisplayString
    }

zbrOptUnsAlrtTrackLogIndex OBJECT-TYPE
    SYNTAX  INTEGER (0..2147483647)
    MAX-ACCESS  read-only
    STATUS  current
    DESCRIPTION
    "Table row number"
    ::= { zbrOptUnsAlrtTrackLogEntry 1 }

zbrOptUnsAlrtTrackLogValue OBJECT-TYPE
  SYNTAX DisplayString (SIZE (0..255))
   MAX-ACCESS read-only
   STATUS current
   DESCRIPTION
   "A Log entry."
   ::= { zbrOptUnsAlrtTrackLogEntry 2 }

zbrOptUnsAlrtTrackLogMaxEntries OBJECT-TYPE
    SYNTAX INTEGER (0..10000)
    MAX-ACCESS read-write
    STATUS current
    DESCRIPTION
    "Maximum number of entries supported by the log"
    ::= { zbrOptUnsAlrtTrackedSettings 4 }

zbrOptUnsAlrtTrackLogClearLog OBJECT-TYPE
   SYNTAX  INTEGER {
       no(1),
       yes(2)    }
   MAX-ACCESS read-write
   STATUS current
   DESCRIPTION
   "Clears the TrackedSettings log when set to yes(2)."
   ::= { zbrOptUnsAlrtTrackedSettings 5 }


--=================================================================================================
--zebra.zbrOptions.zbrOptUnsolictedAlerts.zbrOptUnsAlrtHttp
--=================================================================================================
zbrOptUnsAlrtHttpProxy OBJECT-TYPE
    SYNTAX  OCTET STRING (SIZE (0..2048))
    MAX-ACCESS read-write
    STATUS current
    DESCRIPTION
    " Assigns the URL of the proxy for any HTTP POST alerts."
    ::= { zbrOptUnsAlrtHttp 1 }


--=================================================================================================
--zebra.zbrOptions.zbrOptUnsolictedAlerts.zbrOptUnsAlrtHttp.zbrOptUnsAlrtLogging
--=================================================================================================
zbrOptUnsAlrtLoggingMaxEntries OBJECT-TYPE
   SYNTAX INTEGER (0..10000)
   MAX-ACCESS read-write
   STATUS current
   DESCRIPTION
   " Specifies the maximum number of individual log entries that
   will be stored in the alert.http.logging.entries SGD."
   ::= { zbrOptUnsAlrtLogging 1 }

zbrOptUnsAlrtLoggingClear OBJECT-TYPE
   SYNTAX  INTEGER {
       no(1),
       yes(2)    }
    MAX-ACCESS read-write
   STATUS current
   DESCRIPTION
   " Clears the weblink log entries. Logging is not disabled, the
   log is just cleared out."
   ::= { zbrOptUnsAlrtLogging 2 }


--=================================================================================================
--zebra.zbrOptions.zbrOptUnsolictedAlerts.zbrOptUnsAlrtHttp.zbrOptUnsAlrtAuthentication
--=================================================================================================
zbrOptUnsAlrtAuthenticationAdd OBJECT-TYPE
    SYNTAX  OCTET STRING (SIZE (0..2048))
    MAX-ACCESS read-write
    STATUS current
    DESCRIPTION
    " Allows the user to add a single server/username/password
     triplet into the list of authentication entries. When the printer attempts to connect to the
     server (url specified in alert) the server may require some sort of HTTP authentication
     (e.g. digest, basic, NTLM, etc.). There may be multiple authentication requests along the
     route to the destination (e.g. a local server first requires HTTP authentication as well as
     on the remote server). For each HTTP authentication request received while attempting to connect,
     the printer will enumerate the authentication entries and attempt to satisfy the request
     with the username/password pair provided for the respective server. The server name in the
     entry is what determines which username/password pair should be used for which authentication
     request. Both dns names and IP addresses are acceptable. The server, username, and
     password are separated by a single space (not a tab or other white space character). The
     server name is the only required field. If no username is supplied, but a password is,
     there must be two spaces between the server and the password fields. If there is a
     username but no password, or simply just the servername, no space is required at the
     end of the entry."
    ::= { zbrOptUnsAlrtAuthentication 1 }

zbrOptUnsAlrtAuthenticationRemove OBJECT-TYPE
    SYNTAX  OCTET STRING (SIZE (0..2048))
    MAX-ACCESS read-write
    STATUS current
    DESCRIPTION
    " Allows the user to remove a single server/username/password
     triplet from the list of authentication entries. To remove an entry only the server name
     is supplied however the entire entry will be removed. If an invalid entry is supplied
     no action is taken."
    ::= { zbrOptUnsAlrtAuthentication 2 }

zbrOptUnsAlrtAuthenticationEntries OBJECT-TYPE
    SYNTAX  DisplayString
    MAX-ACCESS read-only
    STATUS current
    DESCRIPTION
    " Lists the server names added to the authentication entries
     list via zbrOptUnsAlrtAuthentication.zbrOptUnsAlrtAuthenticationAdd. Only the server names will be
     shown. The username and passwords will not be shown."
    ::= { zbrOptUnsAlrtAuthentication 3 }

--===========================
-- zebra.zbrOptions.zbrRfid
--===========================

zbrRfidEnable OBJECT-TYPE
    SYNTAX INTEGER {
        on(1),
        off(2)
    }
    MAX-ACCESS read-write
    STATUS current
    DESCRIPTION
    "RFID Reader installed in the printer."
   ::= { zbrRfid 1 }

zbrRfidRegionCode OBJECT-TYPE
   SYNTAX DisplayString (SIZE (0..32))
   MAX-ACCESS read-only
   STATUS current
   DESCRIPTION
   "Region code to define regulatory domain."
   ::= { zbrRfid 2 }

zbrRfidCountryCode OBJECT-TYPE
   SYNTAX DisplayString (SIZE (0..32))
   MAX-ACCESS read-write
   STATUS current
   DESCRIPTION
   "Country code to define regulatory domain."
   ::= { zbrRfid 3 }
   
--===========================
-- zebra.zbrOptions.zbrRfid.zbrRfidPos
--===========================

zbrRfidPosProg OBJECT-TYPE
   SYNTAX DisplayString (SIZE (0..10))
   MAX-ACCESS read-write
   STATUS current
   DESCRIPTION
   "RFID Program Position."
   ::= { zbrRfidPos 1 }

--===========================
-- zebra.zbrOptions.zbrRfid.zbrRfidErrorResponse
--===========================

zbrRfidErrorResponseProg OBJECT-TYPE
   SYNTAX DisplayString (SIZE (0..20))
   MAX-ACCESS read-only
   STATUS current
   DESCRIPTION
   "RFID Error Response."
   ::= { zbrRfidErrorResponse 1 }

--===========================
-- zebra.zbrOptions.zbrRfid.zbrRfidRdr1
--===========================

zbrRfidRdr1Model OBJECT-TYPE
   SYNTAX DisplayString (SIZE (0..10))
   MAX-ACCESS read-only
   STATUS current
   DESCRIPTION
   "RFID Reader Model installed in the printer."
   ::= { zbrRfidRdr1 2 }

zbrRfidRdr1HwVer OBJECT-TYPE
   SYNTAX DisplayString (SIZE (0..10))
   MAX-ACCESS read-only
   STATUS current
   DESCRIPTION
   "RFID Reader Hardware Version."
   ::= { zbrRfidRdr1 3 }

zbrRfidRdr1FwVer OBJECT-TYPE
   SYNTAX DisplayString (SIZE (0..10))
   MAX-ACCESS read-only
   STATUS current
   DESCRIPTION
   "RFID Reader Firmware Version."
   ::= { zbrRfidRdr1 4 }

   
--===========================
-- zebra.zbrOptions.zbrRfid.zbrRfidRdr1.zbrRfidRdr1Pwr
--===========================

zbrRfidRdr1PwrRd OBJECT-TYPE
   SYNTAX INTEGER (0..30)
   MAX-ACCESS read-write
   STATUS current
   DESCRIPTION
   "RFID Reader Read Power Level"
   ::= { zbrRfidRdr1Pwr 1 }

zbrRfidRdr1PwrWr OBJECT-TYPE
   SYNTAX INTEGER (0..30)
   MAX-ACCESS read-write
   STATUS current
   DESCRIPTION
   "RFID Reader Write Power Level"
   ::= { zbrRfidRdr1Pwr 2 }

--===========================
-- zebra.zbrOptions.zbrRfid.zbrRfidRdr1.zbrRfidRdr1Tag
--===========================

zbrRfidRdr1TagCalibrate OBJECT-TYPE
   SYNTAX DisplayString
   MAX-ACCESS read-write
   STATUS current
   DESCRIPTION
   "RFID Calibrate"
   ::= { zbrRfidRdr1Tag 3 }

--===========================
-- zebra.zbrOptions.zbrRfid.zbrRfidRdr1.zbrRfidRdr1Tag.zbrRfidRdr1TagRd
--===========================

zbrRfidRdr1TagRdContent OBJECT-TYPE
   SYNTAX INTEGER {
        epc(1),
        memory-bank-sizes(2),
        protocol-bits(3),
        tid-information(4),
        password-status(5)
    }
    MAX-ACCESS read-write
    STATUS current
    DESCRIPTION
    "RFID Tag Read Contents"
   ::= { zbrRfidRdr1TagRd 1 }

zbrRfidRdr1TagRdResultLine1 OBJECT-TYPE
    SYNTAX DisplayString (SIZE (0..40))
    MAX-ACCESS read-write
    STATUS current
    DESCRIPTION
    "RFID Tag Read Result Line1"
   ::= { zbrRfidRdr1TagRd 2 }
  
zbrRfidRdr1TagRdResultLine2 OBJECT-TYPE
    SYNTAX DisplayString (SIZE (0..40))
    MAX-ACCESS read-write
    STATUS current
    DESCRIPTION
    "RFID Tag Read Result Line2"
   ::= { zbrRfidRdr1TagRd 3 }
   
zbrRfidRdr1TagRdResultLine1Alternate OBJECT-TYPE
    SYNTAX DisplayString (SIZE (0..40))
    MAX-ACCESS read-write
    STATUS current
    DESCRIPTION
    "RFID Tag Read Result LineAlternate1"
   ::= { zbrRfidRdr1TagRd 4 }
   
zbrRfidRdr1TagRdResultLine2Alternate OBJECT-TYPE
    SYNTAX DisplayString (SIZE (0..40))
    MAX-ACCESS read-write
    STATUS current
    DESCRIPTION
    "RFID Tag Read Result LineAlternate2"
   ::= { zbrRfidRdr1TagRd 5 }
   
zbrRfidRdr1TagRdExecute OBJECT-TYPE
    SYNTAX DisplayString (SIZE (0..40))
    MAX-ACCESS read-write
    STATUS current
    DESCRIPTION
    "RFID Tag Read Execute"
   ::= { zbrRfidRdr1TagRd 6 }
     
--===========================
-- zebra.zbrOptions.zbrRfid.zbrRfidRdr1.zbrRfidRdr1Tag.zbrRfidRdr1TagTest
--===========================

zbrRfidRdr1TagTestContent OBJECT-TYPE
   SYNTAX INTEGER {
        read(1),
        write(2),
        quick(3)
    }
    MAX-ACCESS read-write
    STATUS current
    DESCRIPTION
    "RFID Tag Test Contents"
   ::= { zbrRfidRdr1TagTest 1 }

zbrRfidRdr1TagTestResultLine1 OBJECT-TYPE
    SYNTAX DisplayString (SIZE (0..40)) 
    MAX-ACCESS read-write
    STATUS current
    DESCRIPTION
    "RFID Tag Test Result Line1"
   ::= { zbrRfidRdr1TagTest 2 }
  
zbrRfidRdr1TagTestResultLine2 OBJECT-TYPE
    SYNTAX DisplayString (SIZE (0..40))
    MAX-ACCESS read-write
    STATUS current
    DESCRIPTION
    "RFID Tag Test Result Line2"
   ::= { zbrRfidRdr1TagTest 3 }

zbrRfidRdr1TagTestExecute OBJECT-TYPE
    SYNTAX DisplayString (SIZE (0..40))
    MAX-ACCESS read-write
    STATUS current
    DESCRIPTION
    "RFID Tag Test Execute"
   ::= { zbrRfidRdr1TagTest 4 }

--===========================
-- zebra.zbrOptions.zbrRfid.zbrRfidRdr1 Continued
--===========================
zbrRfidRdr1AntennaPort OBJECT-TYPE
   SYNTAX DisplayString (SIZE (0..10))
   MAX-ACCESS read-write
   STATUS current
   DESCRIPTION
   "RFID antenna element selection."
   ::= { zbrRfidRdr1 7 }
--===========================
-- zebra.zbrOptions.zbrRfid Continued
--===========================
zbrRfidHopTableVersion OBJECT-TYPE
   SYNTAX DisplayString (SIZE (0..10))
   MAX-ACCESS read-only
   STATUS current
   DESCRIPTION
   "RFID Hop Table Version."
   ::= { zbrRfid 7 }
        
zbrRfidAntennaSweep OBJECT-TYPE
    SYNTAX INTEGER {
        on(1),
        off(2)
    }
    MAX-ACCESS read-write
    STATUS current
    DESCRIPTION
    "Antenna sweep."
   ::= { zbrRfid 8 }        
   
zbrRfidAdaptiveAntenna OBJECT-TYPE
   SYNTAX INTEGER {
       none(1),
       neighbors(2)
    }
    MAX-ACCESS read-write
    STATUS current
    DESCRIPTION
    "RFID Adaptive Antenna"
   ::= { zbrRfid 9 }
   
zbrRfidRecipeVersion OBJECT-TYPE
   SYNTAX DisplayString (SIZE (0..10))
   MAX-ACCESS read-only
   STATUS current
   DESCRIPTION
   "RFID Recipe Version."
   ::= { zbrRfid 10 }

-- The Next 4 OIDs added as part of AppPlatform Story EFW-2192
zbrRfidVoidPrintLength OBJECT-TYPE
   SYNTAX INTEGER (1..32000)
   MAX-ACCESS read-write
   STATUS current
   DESCRIPTION
   "RFID Void Print Length - a number between 1 and 32000."
   ::= { zbrRfid 11 }

zbrRfidLabelTries OBJECT-TYPE
   SYNTAX INTEGER (1..10)
   MAX-ACCESS read-write
   STATUS current
   DESCRIPTION
   "RFID Label Tries - a number between 1 and 10."
   ::= { zbrRfid 12 }

zbrRfidErrorHandling  OBJECT-TYPE
   SYNTAX INTEGER {
      none(1),
      pause(2),
      error(3)
   }
   MAX-ACCESS read-write
   STATUS current
   DESCRIPTION
   "RFID Error Handling."
   ::= { zbrRfid 13 }

zbrRfidVoidPrintSpeed  OBJECT-TYPE
   SYNTAX DisplayString (SIZE (0..4))
   MAX-ACCESS read-write
   STATUS current
   DESCRIPTION
   "RFID Void Print Speed."
   ::= { zbrRfid 14 }

--====================================================================================
-- zebra.zbrOptions.zbrRfid.zbrRfidHostLog
--====================================================================================
zbrRfidHostLogEnable OBJECT-TYPE
    SYNTAX INTEGER {
        yes(1),
        no(2)
    }
   MAX-ACCESS read-write
   STATUS current
   DESCRIPTION
   "Enables and disables writing to the RFID Log."
   ::= { zbrRfidHostLog 1 }
   
zbrRfidHostLogClear OBJECT-TYPE
   SYNTAX  INTEGER {
       no(1),
       yes(2)    }
   MAX-ACCESS read-write
   STATUS current
   DESCRIPTION
   "Clears the RFID log when set to yes(2)."
   ::= { zbrRfidHostLog 2 }

--====================================================================================
-- zebra.zbrOptions.zbrCradle.zbrCradleComm
--====================================================================================

zbrCradleBaud OBJECT-TYPE
   SYNTAX INTEGER (300..3000000)
   MAX-ACCESS read-write
   STATUS current
   DESCRIPTION
   "The printer's cradle USB-serial port baud rate - one of
   (300,600,1200,2400,4800,9600,19200,38400,57600,115200,230400,460800,921600,1000000,1500000,2000000,3000000)."
   ::= { zbrCradleComm 1 }

zbrCradleHandshake OBJECT-TYPE
    SYNTAX INTEGER {
        rts-cts(1),
        xon-xoff(2),
        none(3)
    }
   MAX-ACCESS read-write
   STATUS current
   DESCRIPTION
    "The printer's cradle USB-serial port handshake"
   ::= { zbrCradleComm 2 }

--===========================
-- zebra.zbrNetmanage.zbrMirror
--===========================

zbrMirrorFeedbackOdometer OBJECT-TYPE
    SYNTAX Unsigned32
    MAX-ACCESS read-write
    STATUS current
    DESCRIPTION
    "Mirror Feedback Odometer"
    ::= { zbrMirror 1 }

zbrMirrorResetDelay OBJECT-TYPE
    SYNTAX INTEGER (0..900)
    MAX-ACCESS read-write
    STATUS current
    DESCRIPTION
    "Mirror Reset Delay"
    ::= { zbrMirror 2 }

zbrMirrorInterface OBJECT-TYPE
   SYNTAX INTEGER {
        both(1),
        wired(2),
        wireless(3)
    }
    MAX-ACCESS read-write
    STATUS current
    DESCRIPTION
    "Mirror Interface"
    ::= { zbrMirror 3 }

zbrMirrorAuto OBJECT-TYPE
   SYNTAX INTEGER {
        on(1),
        off(2)
    }
   MAX-ACCESS read-write
   STATUS current
   DESCRIPTION
   "If 'on', printer will automatically perform a mirror fetch command on power-up, and subsequently
every 'freq' minutes."
   ::= { zbrMirror 4 }

zbrMirrorUsername OBJECT-TYPE
   SYNTAX DisplayString (SIZE (0..20))
   MAX-ACCESS read-write
   STATUS current
   DESCRIPTION
   "Username for FTP logon."
   ::= { zbrMirror 7 }

zbrMirrorPassword OBJECT-TYPE
   SYNTAX DisplayString (SIZE (0..20))
   MAX-ACCESS read-write
   STATUS current
   DESCRIPTION
   "Password for FTP logon."
   ::= { zbrMirror 8 }

zbrMirrorServer OBJECT-TYPE
   SYNTAX DisplayString (SIZE (0..40))
   MAX-ACCESS read-write
   STATUS current
   DESCRIPTION
   "Server ip address or name (if DNS server info is provided via DHCP)."
   ::= { zbrMirror 9 }

zbrMirrorPath OBJECT-TYPE
   SYNTAX DisplayString (SIZE (0..50))
   MAX-ACCESS read-write
   STATUS current
   DESCRIPTION
   "Path on the FTP server where the mirror directory is located."
   ::= { zbrMirror 10 }

zbrMirrorFreq OBJECT-TYPE
   SYNTAX INTEGER (0..65535)
   MAX-ACCESS read-write
   STATUS current
   DESCRIPTION
   "Number of minutes to wait before performing another mirror fetch. If this value is '0', the mirror
    process will only be performed once immediately on power-up. This parameter only applies if
    ip.mirror.auto is 'on'. Caution should be used if setting a low value - otherwise the printer may spend
    most of its time performing the mirror process."
   ::= { zbrMirror 11 }

zbrMirrorFetch OBJECT-TYPE
   SYNTAX INTEGER {
        fetch(1)
    }
   MAX-ACCESS read-write
   STATUS current
   DESCRIPTION
   "Force the mirror process to be run immediately."
   ::= { zbrMirror 12 }

zbrMirrorVersion OBJECT-TYPE
   SYNTAX DisplayString (SIZE (0..100))
   MAX-ACCESS read-only
   STATUS current
   DESCRIPTION
   "The version."
   ::= { zbrMirror 13 }

zbrMirrorFreqHours OBJECT-TYPE
   SYNTAX INTEGER (0..100)
   MAX-ACCESS read-write
   STATUS current
   DESCRIPTION
   "Additional time to wait, in hours, before performing another mirror fetch. See zbrMirror-freq."
   ::= { zbrMirror 14 }

zbrMirrorErrorRetry OBJECT-TYPE
   SYNTAX INTEGER (0..65535)
   MAX-ACCESS read-write
   STATUS current
   DESCRIPTION
   "Error retry time in minutes."
   ::= { zbrMirror 15 }

--===========================
-- zebra.zbrNetmanage.zbrMirror.zbrMirrorFeedback
--===========================

zbrMirrorFeedbackAuto OBJECT-TYPE
   SYNTAX INTEGER {
        on(1),
        off(2)
    }
   MAX-ACCESS read-write
   STATUS current
   DESCRIPTION
   "If on, a feedback file is sent from the printer to the server after each fetch. "
   ::= { zbrMirrorFeedback 1 }

zbrMirrorFeedbackPath OBJECT-TYPE
   SYNTAX DisplayString (SIZE (0..50))
   MAX-ACCESS read-write
   STATUS current
   DESCRIPTION
   "Path on the mirror server where the feedback file will be sent."
   ::= { zbrMirrorFeedback 2 }

zbrMirrorFeedbackFreq OBJECT-TYPE
   SYNTAX INTEGER (0..65535)
   MAX-ACCESS read-write
   STATUS current
   DESCRIPTION
   "Time in minutes between sending the feedback file to the server."
   ::= { zbrMirrorFeedback 3 }

zbrMirrorSuccess OBJECT-TYPE
   SYNTAX INTEGER {
        yes(1),
        no(2)
    }
   MAX-ACCESS read-only
   STATUS current
   DESCRIPTION
   "Success or failure of the last mirror fetch."
   ::= { zbrMirror 21 }

zbrMirrorSuccessTime OBJECT-TYPE
   SYNTAX DisplayString (SIZE (0..100))
   MAX-ACCESS read-only
   STATUS current
   DESCRIPTION
   "Time of the last successful mirror fetch, accurate to seconds."
   ::= { zbrMirror 22 }

zbrMirrorLastTime OBJECT-TYPE
   SYNTAX DisplayString (SIZE (0..100))
   MAX-ACCESS read-only
   STATUS current
   DESCRIPTION
   "Time of the last attempted mirror fetch, accurate to seconds."
   ::= { zbrMirror 23 }

zbrMirrorLastError OBJECT-TYPE
   SYNTAX DisplayString (SIZE (0..255))
   MAX-ACCESS read-only
   STATUS current
   DESCRIPTION
   "Last mirror error."
   ::= { zbrMirror 24 }

zbrMirrorMode OBJECT-TYPE
   SYNTAX INTEGER {
        ftp(1),
        sftp(2)
    }
   MAX-ACCESS read-write
   STATUS current
   DESCRIPTION
   "Mirror ftp mode."
   ::= { zbrMirror 25 }

zbrMirrorApplPath OBJECT-TYPE
   SYNTAX DisplayString (SIZE (0..51))
   MAX-ACCESS read-write
   STATUS current
   DESCRIPTION
   "Complete Explicit Path on the FTP server where the mirror directory is located."
   ::= { zbrMirror 26 }

--===========================
-- zebra.zbrPrint
--===========================

zbrPrintContrast OBJECT-TYPE
   SYNTAX INTEGER (0..3)
   MAX-ACCESS read-write
   STATUS current
   DESCRIPTION
   "Print contrast."
   ::= { zbrPrint 1 }

zbrPrintTone OBJECT-TYPE
   SYNTAX INTEGER (-100..200)
   MAX-ACCESS read-write
   STATUS current
   DESCRIPTION
   "The printer darkness."
   ::= { zbrPrint 2 }

zbrPrintPrintAdj OBJECT-TYPE
   SYNTAX INTEGER (-127..128)
   MAX-ACCESS read-write
   STATUS current
   DESCRIPTION
   "Print adjust."
   ::= { zbrPrint 4 }

zbrPrintMediaControlPrintSpeed OBJECT-TYPE
    SYNTAX DisplayString (SIZE (0..3))
    MAX-ACCESS read-write
    STATUS current
    DESCRIPTION
    "Media Control Print Speed - floating point number between 1.0 and 4.0"
    ::= { zbrPrint 5 }

zbrPrintTotalLabelsInBatch OBJECT-TYPE
    SYNTAX INTEGER (0..65535)
    MAX-ACCESS read-only
    STATUS current
    DESCRIPTION
    "Total labels in batch"
    ::= { zbrPrint 6 }

zbrPrintLabelsRemainingInBatch OBJECT-TYPE
    SYNTAX INTEGER (0..65535)
    MAX-ACCESS read-only
    STATUS current
    DESCRIPTION
    "Labels remaining in batch"
    ::= { zbrPrint 7 }

zbrPrintConfigLostError OBJECT-TYPE
    SYNTAX  INTEGER {
        no(1),
        yes(2)
    }
    MAX-ACCESS read-only
    STATUS current
    DESCRIPTION
   "Configuration Lost Error"
   ::= { zbrPrint 8 }

zbrPrintRamAllocationError OBJECT-TYPE
    SYNTAX  INTEGER {
        no(1),
        yes(2)
    }
    MAX-ACCESS read-only
    STATUS current
    DESCRIPTION
   "Ram Allocation Error"
   ::= { zbrPrint 9 }

zbrPrintBitmapAllocationError OBJECT-TYPE
    SYNTAX  INTEGER {
        no(1),
        yes(2)
    }
    MAX-ACCESS read-only
    STATUS current
    DESCRIPTION
   "Bitmap Allocation Error"
   ::= { zbrPrint 10 }

zbrPrintStoredFormatError OBJECT-TYPE
    SYNTAX  INTEGER {
        no(1),
        yes(2)
    }
    MAX-ACCESS read-only
    STATUS current
    DESCRIPTION
   "Stored Format Error"
   ::= { zbrPrint 11 }

zbrPrintStoredGraphicError OBJECT-TYPE
    SYNTAX  INTEGER {
        no(1),
        yes(2)
    }
    MAX-ACCESS read-only
    STATUS current
    DESCRIPTION
   "Stored Graphic Error"
    ::= { zbrPrint 12 }

zbrPrintStoredBitmapError OBJECT-TYPE
    SYNTAX  INTEGER {
        no(1),
        yes(2)
    }
    MAX-ACCESS read-only
    STATUS current
    DESCRIPTION
   "Stored Bitmap Error"
   ::= { zbrPrint 13 }

zbrPrintStoredFontError OBJECT-TYPE
    SYNTAX  INTEGER {
        no(1),
        yes(2)
    }
    MAX-ACCESS read-only
    STATUS current
    DESCRIPTION
   "Stored Font Error"
   ::= { zbrPrint 14 }

zbrPrintCacheMemoryError OBJECT-TYPE
    SYNTAX  INTEGER {
        no(1),
        yes(2)
    }
    MAX-ACCESS read-only
    STATUS current
    DESCRIPTION
   "Cache Memory Error"
   ::= { zbrPrint 15 }

zbrPrintBasicForcedError OBJECT-TYPE
    SYNTAX  INTEGER {
        no(1),
        yes(2)
    }
    MAX-ACCESS read-only
    STATUS current
    DESCRIPTION
   "Basic Forced Error"
    ::= { zbrPrint 16 }

zbrPrintRibbonInWarning OBJECT-TYPE
    SYNTAX  INTEGER {
        no(1),
        yes(2)
    }
    MAX-ACCESS read-only
    STATUS current
    DESCRIPTION
   "Ribbon In Warning"
   ::= { zbrPrint 17 }

zbrPrintBufferFullError OBJECT-TYPE
    SYNTAX  INTEGER {
        no(1),
        yes(2)
    }
    MAX-ACCESS read-only
    STATUS current
    DESCRIPTION
   "Buffer Full Error"
   ::= { zbrPrint 18 }

zbrPrintCutterJamError OBJECT-TYPE
    SYNTAX  INTEGER {
        no(1),
        yes(2)
    }
    MAX-ACCESS read-only
    STATUS current
    DESCRIPTION
   "Cutter Jam Error"
   ::= { zbrPrint 19 }

zbrPrintNumberOfFormats OBJECT-TYPE
    SYNTAX INTEGER (0..65535)
    MAX-ACCESS read-only
    STATUS current
    DESCRIPTION
    "Number Of Formats"
   ::= { zbrPrint 20 }

zbrPrintPartialFormatInProgress OBJECT-TYPE
    SYNTAX  INTEGER {
        no(1),
        yes(2)
    }
    MAX-ACCESS read-only
    STATUS current
    DESCRIPTION
   "Partial Format In Progress"
    ::= { zbrPrint 21 }

zbrPrintPause OBJECT-TYPE
    SYNTAX  INTEGER {
        no(1),
        yes(2)
    }
    MAX-ACCESS read-only
    STATUS current
    DESCRIPTION
   "Printer Paused"
    ::= { zbrPrint 22 }

zbrPrintPaperOut OBJECT-TYPE
    SYNTAX  INTEGER {
        no(1),
        yes(2)
    }
    MAX-ACCESS read-only
    STATUS current
    DESCRIPTION
   "Paper Out"
    ::= { zbrPrint 23 }

zbrPrintRibbonOut OBJECT-TYPE
    SYNTAX  INTEGER {
        no(1),
        yes(2)
    }
    MAX-ACCESS read-only
    STATUS current
    DESCRIPTION
   "Ribbon Out"
    ::= { zbrPrint 24 }

zbrToneFormat OBJECT-TYPE
    SYNTAX  INTEGER {
        cpcl(1),
        zpl(2)
    }
    MAX-ACCESS read-write
    STATUS current
    DESCRIPTION
   "Print Tone Format"
    ::= { zbrPrint 25 }

zbrPrintToneZpl OBJECT-TYPE
   SYNTAX DisplayString (SIZE (0..5))
   MAX-ACCESS read-write
   STATUS current
   DESCRIPTION
   "The printer darkness in ZPL format - floating point number from 0.0 to 30.0."
   ::= { zbrPrint 26 }
        
zbrRibbonLowWarning OBJECT-TYPE
   SYNTAX INTEGER {
      ribbon-low-threshold-off(1),
      ribbon-low-threshold-on(2),
      ribbon-low-threshold-5-meters(5),
      ribbon-low-threshold-10-meters(10),
      ribbon-low-threshold-15-meters(15),
      ribbon-low-threshold-25-meters(25),
      ribbon-low-threshold-50-meters(50),
      ribbon-low-threshold-75-meters(75),
      ribbon-low-threshold-100-meters(100)
   }
   MAX-ACCESS read-write
   STATUS current
   DESCRIPTION
    "Ribbon-low threshold, meters."
   ::= { zbrPrint 27 }

zbrTroubleshootingLabelChoices OBJECT-TYPE
    SYNTAX  INTEGER {
        darkness(1),
        first-dot-location(2),
        print-line(3),
        image-compression(4),
        element-out(5)
    }
    MAX-ACCESS read-write
    STATUS current
    DESCRIPTION
   "Troubleshooting Label Choices"
    ::= { zbrPrint 28 }

zbrTroubleshootingLabelPrint OBJECT-TYPE
    SYNTAX  DisplayString (SIZE (0..255))
    MAX-ACCESS  read-write
    STATUS  current
    DESCRIPTION
    "Print selected troubleshooting label"
    ::= { zbrPrint 29 }

zbrColdTempComp OBJECT-TYPE
   SYNTAX INTEGER {
        on(1),
        off(2)
    }
   MAX-ACCESS read-write
   STATUS current
   DESCRIPTION
   "ON - improves image quality in cold environments."
   ::= { zbrPrint 30 }
    
zbrLegacyCompatibility OBJECT-TYPE
   SYNTAX INTEGER {
        on(1),
        off(2)
    }
   MAX-ACCESS read-write
   STATUS current
   DESCRIPTION
   "Turn on/off legacy compatibility print quality."
   ::= { zbrPrint 31 }
   
zbrDarknessMode OBJECT-TYPE
   SYNTAX INTEGER {
        cartridge(1),
        user(2),
        relative(3)
    }
   MAX-ACCESS read-only
   STATUS current
   DESCRIPTION
   "Darkness control mode for cartridged based media."
   ::= { zbrPrint 32 }
   
zbrLabelInvert OBJECT-TYPE
   SYNTAX INTEGER {
        on(1),
        off(2)
    }
   MAX-ACCESS read-write
   STATUS current
   DESCRIPTION
   "Turn on/off label inversion."
   ::= { zbrPrint 33 }
   
zbrPrintXiCompatibilityAdjust OBJECT-TYPE
   SYNTAX DisplayString (SIZE (0..5))
   MAX-ACCESS read-write
   STATUS current
   DESCRIPTION
   " vertical scaling percentage for backwards compatibility with Xi4"
   ::= { zbrPrint 34 }
   
--=================================================================================================
--zebra.zbrControl
--=================================================================================================

zbrControlPause OBJECT-TYPE
    SYNTAX  INTEGER {
        no(1),
        yes(2)
    }
    MAX-ACCESS  read-write
    STATUS  current
    DESCRIPTION
    "A value of 2 will pause the printer."
    ::= { zbrControl 1 }

zbrControlFeedLabel OBJECT-TYPE
    SYNTAX  INTEGER {
        no(1),
        yes(2)
    }
    MAX-ACCESS  read-write
    STATUS  current
    DESCRIPTION
    "A value of 2 will feed a label."
    ::= { zbrControl 2 }

zbrControlCancelOne OBJECT-TYPE
    SYNTAX  INTEGER {
        no(1),
        yes(2)
    }
    MAX-ACCESS  read-write
    STATUS  current
    DESCRIPTION
    "A value of 2 will cancel the job currently printing."
    ::= { zbrControl 3 }

zbrControlCancelAll OBJECT-TYPE
    SYNTAX  INTEGER {
        no(1),
        yes(2)
    }
    MAX-ACCESS  read-write
    STATUS  current
    DESCRIPTION
    "A value of 2 will cancel all jobs queued for printing."
    ::= { zbrControl 4 }

zbrControlResetPrinter OBJECT-TYPE
    SYNTAX  INTEGER {
        no(1),
        yes(2)
    }
    MAX-ACCESS  read-write
    STATUS  current
    DESCRIPTION
    "A value of 2 will reset the printer."
    ::= { zbrControl 5 }

zbrControlSaveSettings OBJECT-TYPE
    SYNTAX  INTEGER {
        no(1),
        yes(2)
    }
    MAX-ACCESS  read-write
    STATUS  current
    DESCRIPTION
    "A value of 2 will save the current printer settings."
    ::= { zbrControl 6 }

zbrControlLoadLastSaved OBJECT-TYPE
    SYNTAX  INTEGER {
        no(1),
        yes(2)
    }
    MAX-ACCESS  read-write
    STATUS  current
    DESCRIPTION
    "A value of 2 will recall the last saved settings."
    ::= { zbrControl 7 }

zbrControlLoadDefaults OBJECT-TYPE
    SYNTAX  INTEGER {
        no(1),
        yes(2)
    }
    MAX-ACCESS  read-write
    STATUS  current
    DESCRIPTION
    "A value of 2 will reload factory settings."
    ::= { zbrControl 8 }

zbrPrintCutNow OBJECT-TYPE
    SYNTAX  INTEGER {
        no(1),
        yes(2)
    }
    MAX-ACCESS read-write
    STATUS current
    DESCRIPTION
    "A value of 2 will trigger the cutter."
    ::= { zbrControl 9 }

zbrControlUnpause OBJECT-TYPE
    SYNTAX  INTEGER {
        no(1),
        yes(2)
    }
    MAX-ACCESS  read-write
    STATUS  current
    DESCRIPTION
    "A value of 2 will unpause the printer."
    ::= { zbrControl 10 }

zbrControlReprint OBJECT-TYPE
    SYNTAX  INTEGER {
        no(1),
        yes(2)
    }
    MAX-ACCESS  read-write
    STATUS  current
    DESCRIPTION
    "A value of 2 will reprint the last printed label."
    ::= { zbrControl 11 }

--===========================
-- zebra.zbrSettings
--===========================

zbrSettingsTearOffPosition OBJECT-TYPE
   SYNTAX INTEGER
    MAX-ACCESS read-write
    STATUS current
    DESCRIPTION
    "Tear-Off Position. The allowable range is dependant on your printer model."
    ::= { zbrSettings 1 }

zbrSettingsMediaTracking OBJECT-TYPE
   SYNTAX INTEGER {
        bar(1),
        gap(2)
    }
    MAX-ACCESS read-write
    STATUS current
    DESCRIPTION
    "Media Tracking."
    ::= { zbrSettings 2 }

zbrSettingsMediaType OBJECT-TYPE
   SYNTAX INTEGER {
        label(1),
        journal(2)
    }
    MAX-ACCESS read-write
    STATUS current
    DESCRIPTION
    "Media Type."
    ::= { zbrSettings 3 }

zbrSettingsPrintWidth OBJECT-TYPE
   SYNTAX INTEGER
   MAX-ACCESS read-write
   STATUS current
   DESCRIPTION
    "Print Width Setting"
    ::= { zbrSettings 4 }

zbrSettingsWarnIfHeadCold OBJECT-TYPE
   SYNTAX  INTEGER {
       no(1),
       yes(2)
    }
    MAX-ACCESS read-write
    STATUS current
    DESCRIPTION
    "Head Cold Warning Active"
    ::= { zbrSettings 5 }

zbrSettingsCommandPrefix OBJECT-TYPE
    SYNTAX INTEGER (1..255)
    MAX-ACCESS read-write
    STATUS current
    DESCRIPTION
    "Command Prefix"
    ::= { zbrSettings 6 }

zbrSettingsFormattingPrefix OBJECT-TYPE
    SYNTAX INTEGER (1..255)
    MAX-ACCESS read-write
    STATUS current
    DESCRIPTION
    "Formatting Prefix"
    ::= { zbrSettings 7 }

zbrSettingsDelimiter OBJECT-TYPE
    SYNTAX INTEGER (1..255)
    MAX-ACCESS read-write
    STATUS current
    DESCRIPTION
    "Parameter Delimiter"
    ::= { zbrSettings 8 }

zbrSettingsLabelDescriptionLanguage OBJECT-TYPE
    SYNTAX INTEGER {
        zpl-1(1),
        zpl-2(2)
    }
    MAX-ACCESS read-write
    STATUS current
    DESCRIPTION
    "Label Description Language"
    ::= { zbrSettings 9 }

zbrSettingsBackfeedPercent OBJECT-TYPE
   SYNTAX INTEGER {
        backfeed-before(1),
        backfeed-10-percent(10),
        backfeed-20-percent(20),
        backfeed-30-percent(30),
        backfeed-40-percent(40),
        backfeed-50-percent(50),
        backfeed-60-percent(60),
        backfeed-70-percent(70),
        backfeed-80-percent(80),
        backfeed-default(90),
        backfeed-after(100),
        backfeed-off(110)
    }
    MAX-ACCESS read-write
    STATUS current
    DESCRIPTION
    "Backfeed Setting"
    ::= { zbrSettings 10 }

zbrSettingsHeadTestFatal OBJECT-TYPE
    SYNTAX INTEGER {
        no(1),
        yes(2)
    }
    MAX-ACCESS read-only
    STATUS deprecated
    DESCRIPTION
    "This turns on the head test option. When activated, this causes the printer to halt
    when a head test failure is encountered. Once an error is encountered the printer remains
    in error mode until the head test is turned off or power is cycled."
    ::= { zbrSettings 11 }

zbrSettingsLabelTop OBJECT-TYPE
   SYNTAX INTEGER
    MAX-ACCESS read-write
    STATUS current
    DESCRIPTION
    "Label Top"
    ::= { zbrSettings 12 }

zbrSettingsPrintMode  OBJECT-TYPE
   SYNTAX INTEGER {
        rewind(1),
        tear-off(2),
        peel-off(3),
        cutter(4),
        delayed-cut(5),
        applicator(6),
        linerless-peel(7),
        linerless-rewind(8),
        rfid(9),
        linerless-tear(10),
        linerless-cut(11),
        linerless-delay-cut(12),
        partial-cut(13),
        partial-delay-cut(14),
        stream(15)
        
    }
    MAX-ACCESS read-write
    STATUS current
    DESCRIPTION
    "Print Mode"
    ::= { zbrSettings 13 }

zbrSettingsPrintMethod OBJECT-TYPE
   SYNTAX INTEGER {
       thermal-transfer(1),
       direct-thermal(2)
    }
    MAX-ACCESS read-write
    STATUS current
    DESCRIPTION
    "Print Method"
    ::= { zbrSettings 14 }

zbrSettingsMaxLabelLength OBJECT-TYPE
   SYNTAX INTEGER {
        length-1-inches-25-mm(1),
        length-2-inches-50-mm(2),
        length-3-inches-76-mm(3),
        length-4-inches-101-mm(4),
        length-5-inches-126-mm(5),
        length-6-inches-152-mm(6),
        length-7-inches-177-mm(7),
        length-8-inches-202-mm(8),
        length-9-inches-228-mm(9),
        length-10-inches-253-mm(10),
        length-11-inches-278-mm(11),
        length-12-inches-304-mm(12),
        length-13-inches-329-mm(13),
        length-14-inches-354-mm(14),
        length-15-inches-380-mm(15),
        length-16-inches-405-mm(16),
        length-17-inches-430-mm(17),
        length-18-inches-456-mm(18),
        length-19-inches-481-mm(19),
        length-20-inches-506-mm(20),
        length-21-inches-532-mm(21),
        length-22-inches-557-mm(22),
        length-23-inches-582-mm(23),
        length-24-inches-608-mm(24),
        length-25-inches-633-mm(25),
        length-26-inches-658-mm(26),
        length-27-inches-684-mm(27),
        length-28-inches-709-mm(28),
        length-29-inches-734-mm(29),
        length-30-inches-760-mm(30),
        length-31-inches-785-mm(31),
        length-32-inches-810-mm(32),
        length-33-inches-836-mm(33),
        length-34-inches-861-mm(34),
        length-35-inches-886-mm(35),
        length-36-inches-912-mm(36),
        length-37-inches-937-mm(37),
        length-38-inches-962-mm(38),
        length-39-inches-988-mm(39)
    }
    MAX-ACCESS read-write
    STATUS current
    DESCRIPTION
    "Maximum Label Length"
    ::= { zbrSettings 15 }

zbrSettingsProtocol OBJECT-TYPE
    SYNTAX INTEGER {
        zebra(1),
        ack-nak(2),
        none(3)
    }
    MAX-ACCESS read-write
    STATUS current
    DESCRIPTION
    "Protocol"
    ::= { zbrSettings 16 }

zbrSettingsNetworkId OBJECT-TYPE
    SYNTAX INTEGER (0..999)
    MAX-ACCESS read-write
    STATUS current
    DESCRIPTION
    "Network Id"
    ::= { zbrSettings 17 }

zbrSettingsHexDump OBJECT-TYPE
   SYNTAX INTEGER {
        off(1),
        on(2)
    }
    MAX-ACCESS read-write
    STATUS current
   DESCRIPTION
    "Communications Mode"
    ::= { zbrSettings 18 }

zbrSettingsLeftPosition OBJECT-TYPE
    SYNTAX INTEGER (-9999..9999)
    MAX-ACCESS read-write
    STATUS current
    DESCRIPTION
    "Left Position"
    ::= { zbrSettings 19 }

zbrSettingsFormatConvert OBJECT-TYPE
    SYNTAX INTEGER {
        format-convert-150-300(1),
        format-convert-150-600(2),
        format-convert-200-600(3),
        format-convert-300-600(4),
        format-convert-none(5)
    }
    MAX-ACCESS read-write
    STATUS current
    DESCRIPTION
    "Format Convert Setting"
    ::= { zbrSettings 20 }

zbrSettingsLanguage OBJECT-TYPE
    SYNTAX INTEGER {
        english(1),
        spanish(2),
        french(3),
        german(4),
        italian(5),
        norwegian(6),
        portuguese(7),
        swedish(8),
        danish(9),
        spanish2(10),
        dutch(11),
        finnish(12),
        japanese(13),
        korean(14),
        simpchinese(15),
        tradchinese(16),
        russian(17),
        polish(18),
        czech(19),
        romanian(20)
    }
    MAX-ACCESS read-write
    STATUS current
    DESCRIPTION
    "Language"
    ::= { zbrSettings 21 }
    
zbrSettingsMediaDraftMode OBJECT-TYPE
   SYNTAX INTEGER {
        off(1),
        on(2)
    }
    MAX-ACCESS  read-write
    STATUS  current
    DESCRIPTION
    "Media Draft Mode"
    ::= { zbrSettings 22 }

zbrSettingsMediaDynamicLengthCalibration OBJECT-TYPE
   SYNTAX INTEGER {
        off(1),
        on(2)
    }
    MAX-ACCESS  read-write
    STATUS  current
    DESCRIPTION
    "Media Dynamic Length Calibration"
    ::= { zbrSettings 23 }


--===============================================================
-- zebra.zbrSettings.zbrSettingsMediaFeed
--===============================================================

zbrSettingsMediaFeedPowerUp OBJECT-TYPE
   SYNTAX INTEGER {
       feed-action(1),
        calibrate-action(2),
        set-label-length-action(3),
        threshold-label-length-action(4),
        no-action(5),
        quick-cal(6)
    }
    MAX-ACCESS read-write
    STATUS current
    DESCRIPTION
    "Media Feed/Power Up"
    ::= { zbrSettingsMediaFeed 1 }

zbrSettingsMediaFeedHeadClose OBJECT-TYPE
    SYNTAX INTEGER {
       feed-action(1),
        calibrate-action(2),
        set-label-length-action(3),
        threshold-label-length-action(4),
        no-action(5),
        quick-cal(6)
    }
    MAX-ACCESS read-write
    STATUS current
    DESCRIPTION
    "Media Feed/Head Close"
    ::= { zbrSettingsMediaFeed 2 }

zbrSettingsSensorBarGain OBJECT-TYPE
    SYNTAX INTEGER (0..255)
    MAX-ACCESS read-write
    STATUS current
    DESCRIPTION
    "Bar Sensor Gain Setting"
    ::= { zbrSettingsSensorBar 1 }

zbrSettingsSensorBarOffset OBJECT-TYPE
    SYNTAX INTEGER (0..255)
    MAX-ACCESS read-write
    STATUS current
    DESCRIPTION
    "Bar Sensor Offset Setting"
    ::= { zbrSettingsSensorBar 2 }

zbrSettingsSensorBarBrightness OBJECT-TYPE
    SYNTAX INTEGER (0..255)
    MAX-ACCESS read-write
    STATUS current
    DESCRIPTION
    "Bar Sensor LED Brightness Setting"
    ::= { zbrSettingsSensorBar 3 }

zbrSettingsSensorBarThreshold OBJECT-TYPE
    SYNTAX INTEGER (0..255)
    MAX-ACCESS read-write
    STATUS current
    DESCRIPTION
    "Bar Sensor Bar Threshold Setting"
    ::= { zbrSettingsSensorBar 4 }

zbrSettingsSensorBarMediaOutThreshold OBJECT-TYPE
    SYNTAX INTEGER (0..255)
    MAX-ACCESS read-write
    STATUS current
    DESCRIPTION
    "Bar Sensor Media Out Threshold Setting"
    ::= { zbrSettingsSensorBar 5 }

zbrSettingsSensorBarLocation OBJECT-TYPE
   SYNTAX INTEGER {
        front(1),
        back(2)
    }
    MAX-ACCESS read-write
    STATUS current
    DESCRIPTION
    "Bar Sensor Location Selector"
    ::= { zbrSettingsSensorBar 6 }

zbrSettingsSensorGapGain OBJECT-TYPE
    SYNTAX INTEGER (0..255)
    MAX-ACCESS read-write
    STATUS current
    DESCRIPTION
    "Gap Sensor Gain Setting"
    ::= { zbrSettingsSensorGap 1 }

zbrSettingsSensorGapOffset OBJECT-TYPE
    SYNTAX INTEGER (0..255)
    MAX-ACCESS read-write
    STATUS current
    DESCRIPTION
    "Gap Sensor Offset Setting"
    ::= { zbrSettingsSensorGap 2 }

zbrSettingsSensorGapBrightness OBJECT-TYPE
    SYNTAX INTEGER (0..255)
    MAX-ACCESS read-write
    STATUS current
    DESCRIPTION
    "Gap Sensor LED Brightness Setting"
    ::= { zbrSettingsSensorGap 3 }

zbrSettingsSensorGapThreshold OBJECT-TYPE
    SYNTAX INTEGER (0..255)
    MAX-ACCESS read-write
    STATUS current
    DESCRIPTION
    "Gap Sensor Gap Threshold Setting"
    ::= { zbrSettingsSensorGap 4 }

zbrSettingsSensorGapMediaOutThreshold OBJECT-TYPE
    SYNTAX INTEGER (0..255)
    MAX-ACCESS read-write
    STATUS current
    DESCRIPTION
    "Gap Sensor Media Out Threshold Setting"
    ::= { zbrSettingsSensorGap 5 }

zbrSettingsSensorRibbonGain OBJECT-TYPE
    SYNTAX INTEGER (0..255)
    MAX-ACCESS read-write
    STATUS current
    DESCRIPTION
    "Ribbon Sensor Gain Setting"
    ::= { zbrSettingsSensorRibbon 1 }

zbrSettingsSensorRibbonOffset OBJECT-TYPE
    SYNTAX INTEGER (0..255)
    MAX-ACCESS read-write
    STATUS current
    DESCRIPTION
    "Ribbon Sensor Offset Setting"
    ::= { zbrSettingsSensorRibbon 2 }

zbrSettingsSensorRibbonBrightness OBJECT-TYPE
    SYNTAX INTEGER (0..255)
    MAX-ACCESS read-write
    STATUS current
    DESCRIPTION
    "Ribbon Sensor LED Brightness Setting"
    ::= { zbrSettingsSensorRibbon 3 }

zbrSettingsSensorRibbonThreshold OBJECT-TYPE
    SYNTAX INTEGER (0..255)
    MAX-ACCESS read-write
    STATUS current
    DESCRIPTION
    "Ribbon Sensor Ribbon Threshold"
    ::= { zbrSettingsSensorRibbon 4 }

zbrSensorSelfAdjustingEnable OBJECT-TYPE
    SYNTAX INTEGER {
        yes(1),
        no(2)
    }
   MAX-ACCESS read-write
   STATUS current
   DESCRIPTION
   "Enables and disables the self-adjusting sensor."
   ::= { zbrSettingsSensorSelfAdjusting 1 }

zbrSensorSelect OBJECT-TYPE
   SYNTAX INTEGER {
      reflective (1),
      transmissive (2)
   }
   MAX-ACCESS read-write
   STATUS current
   DESCRIPTION
   "The sensor opacity."
   ::= { zbrSettingsSensors 10 }
   
zbrCoverOpen OBJECT-TYPE
    SYNTAX INTEGER {
        yes(1),
        no(2)
    }
   MAX-ACCESS read-only
   STATUS current
   DESCRIPTION
   "The status of the media cover."
   ::= { zbrSettingsSensors 15 }

zbrSensorProfile OBJECT-TYPE
   SYNTAX INTEGER {
      print (1),
      store (2),
      usb-host (3),
      reply (4)
   }
   MAX-ACCESS read-write
   STATUS current
   DESCRIPTION
   "Sensor output destination options."
   ::= { zbrSettingsSensors 16 }

zbrSensorRecallFactoryCal OBJECT-TYPE
    SYNTAX  INTEGER {
        no(1),
        yes(2)
    }
    MAX-ACCESS  read-write
    STATUS  current
    DESCRIPTION
    "A value of 2 will restore the factory calibrated values for all sensor settings."
   ::= { zbrSettingsSensors 20 }

zbrCoverOpenEnable OBJECT-TYPE
    SYNTAX INTEGER {
        yes(1),
        no(2)
    }
   MAX-ACCESS read-write
   STATUS current
   DESCRIPTION
   "The configuration if media cover open should be reported."
   ::= { zbrSettingsSensors 21 }

--===========================
-- zebra.zbrFile
--===========================
zbrFilePersistent OBJECT-TYPE
    SYNTAX DisplayString (SIZE (0..100))
    MAX-ACCESS read-write
    STATUS current
    DESCRIPTION
    "Make file persistent"
    ::= { zbrFile 1 }

zbrFileDriveInfo OBJECT-TYPE
    SYNTAX OCTET STRING (SIZE (0..64995))
    MAX-ACCESS read-write
    STATUS current
    DESCRIPTION
    "Get drive information"
    ::= { zbrFile 2 }
      
zbrFileCaptureResponseBegin OBJECT-TYPE
    SYNTAX DisplayString (SIZE (1..20))
    MAX-ACCESS read-write
    STATUS current
    DESCRIPTION
    "Begin the output capture to specified file"
    ::= { zbrFile 3 }
    
zbrFileCaptureResponseEnd OBJECT-TYPE
    SYNTAX DisplayString (SIZE (0..1))
    MAX-ACCESS read-write
    STATUS current
    DESCRIPTION
    "Terminate the output capture to file"
    ::= { zbrFile 4 }

zbrFileCaptureResponseDestination OBJECT-TYPE
   SYNTAX INTEGER {
         printer-file(1),
         usb-file(2)
    }
   MAX-ACCESS read-write
   STATUS current
   DESCRIPTION
    "Destination where the output capture file is saved."
      ::= { zbrFile 5 }
      
--===========================
-- zebra.zbrFile.zbrFileCert
--===========================

zbrFileCertExpiration OBJECT-TYPE
    SYNTAX OCTET STRING (SIZE (0..64995))
    MAX-ACCESS read-only
    STATUS current
    DESCRIPTION
    "Get certificate expiration information"
    ::= { zbrFileCert  1 }

zbrFileCertSupportedCurves OBJECT-TYPE
    SYNTAX OCTET STRING (SIZE (0..64995))
    MAX-ACCESS read-only
    STATUS current
    DESCRIPTION
    "Get elliptical curves supported"
    ::= { zbrFileCert  2 }

--===========================
-- zebra.zbrDevice
--===========================

zbrDevicePrintGeometryRevision OBJECT-TYPE
    SYNTAX DisplayString (SIZE (0..1))
    MAX-ACCESS read-only
    STATUS current
    DESCRIPTION
    "Revision character of the print mechanism geometry"
    ::= { zbrDevice 1 }

zbrDeviceSlot1 OBJECT-TYPE
    SYNTAX DisplayString (SIZE (0..20))
    MAX-ACCESS read-only
    STATUS current
    DESCRIPTION
    "Reports the contents of option slot 1"
    ::= { zbrDevice 2 }

zbrDeviceSlot2 OBJECT-TYPE
    SYNTAX DisplayString (SIZE (0..20))
    MAX-ACCESS read-only
    STATUS current
    DESCRIPTION
    "Reports the contents of option slot 2"
    ::= { zbrDevice 3 }

zbrDeviceDocked OBJECT-TYPE
   SYNTAX INTEGER {
      no(1),
      yes(2)
    }
    MAX-ACCESS read-only
    STATUS current
    DESCRIPTION
    "Device Docked."
    ::= { zbrDevice 4 }

    
--===========================
-- zebra.zbrDevice.zbrLight
--===========================
zbrHeadOpenBrightness OBJECT-TYPE
    SYNTAX INTEGER {
        off(1),
        low(2),
        medium(3),
        high(4)
    }
   MAX-ACCESS read-write
   STATUS current
   DESCRIPTION
   "The Head Open Light Brightness setting."
   ::= { zbrLight 1 }

zbrCoverOpenBrightness OBJECT-TYPE
    SYNTAX INTEGER {
        off(1),
        low(2),
        medium(3),
        high(4)
    }
   MAX-ACCESS read-write
   STATUS current
   DESCRIPTION
   "The Cover Open Light Brightness setting."
   ::= { zbrLight 2 }

zbrRibbonPathBrightness OBJECT-TYPE
    SYNTAX INTEGER {
        off(1),
        low(2),
        medium(3),
        high(4)
    }
   MAX-ACCESS read-write
   STATUS current
   DESCRIPTION
   "The Ribbon Path Light Brightness setting."
   ::= { zbrLight 3 }

zbrMediaPathBrightness OBJECT-TYPE
    SYNTAX INTEGER {
        off(1),
        low(2),
        medium(3),
        high(4)
    }
   MAX-ACCESS read-write
   STATUS current
   DESCRIPTION
   "The Media Path Light Brightness setting."
   ::= { zbrLight 4 }

--===========================
-- zebra.zbrDevice.zbrSyslog
--===========================
zbrSyslogEnable OBJECT-TYPE
   SYNTAX INTEGER {
        on(1),
        off(2)
    }
   MAX-ACCESS read-write
   STATUS current
   DESCRIPTION
   "Enable syslog"
   ::= { zbrSyslog 1 }

zbrSyslogConfiguration OBJECT-TYPE
   SYNTAX OCTET STRING (SIZE (0..1000))
   MAX-ACCESS read-write
   STATUS current
   DESCRIPTION
   "Configure syslog (ex. debug,server_name;alert,local)"
   ::= { zbrSyslog 2 }
   
zbrSyslogSaveLocalFile OBJECT-TYPE
   SYNTAX INTEGER {
        yes(1),
        no(2)
    }
   MAX-ACCESS read-write
   STATUS current
   DESCRIPTION
   "Save syslog to E drive if 'local' is specified in configuration"
   ::= { zbrSyslog 3 }
   
zbrSyslogLogMaxFileSize OBJECT-TYPE
   SYNTAX INTEGER (10000..400000)
   MAX-ACCESS read-write
   STATUS current
   DESCRIPTION
   "Maximum size of the local syslog"
   ::= { zbrSyslog 4 }
   
zbrSyslogEntries OBJECT-TYPE
   SYNTAX OCTET STRING (SIZE (0..64995))
   MAX-ACCESS read-only
   STATUS current
   DESCRIPTION
   "Display content of local syslog"
   ::= { zbrSyslog 5 }
   
zbrSyslogClearLog OBJECT-TYPE
   SYNTAX OCTET STRING (SIZE (0..1000))
   MAX-ACCESS read-write
   STATUS current
   DESCRIPTION
   "Clears the local syslog"
   ::= { zbrSyslog 6 }
   
--===========================
-- zebra.zbrDevice.zbrFeature
--===========================
   
zbrFeatureMfi OBJECT-TYPE
    SYNTAX INTEGER {
        not-available(1),
        not-present(2),
        present(3)
    }
    MAX-ACCESS read-only
    STATUS current
    DESCRIPTION
    "MFi Feature Support."
    ::= { zbrFeature 1 }
   
zbrFeatureMcr OBJECT-TYPE
    SYNTAX INTEGER {
        not-available(1),
        not-present(2),
        present(3)
    }
    MAX-ACCESS read-only
    STATUS current
    DESCRIPTION
    "Magnetic card reader is installed."
    ::= { zbrFeature 2 }

zbrFeatureBluetoothLe OBJECT-TYPE
    SYNTAX INTEGER {
        not-available(1),
        not-present(2),
        present(3)
    }
    MAX-ACCESS read-only
    STATUS current
    DESCRIPTION
    "Bluetooth LE radio is installed."
    ::= { zbrFeature 3 }
    
zbrFeatureNfc OBJECT-TYPE
    SYNTAX INTEGER {
        not-available(1),
        not-present(2),
        present(3)
    }
    MAX-ACCESS read-only
    STATUS current
    DESCRIPTION
    "NFC reader is installed."
    ::= { zbrFeature 4 }
   
zbrFeatureRibbonCartridge OBJECT-TYPE
    SYNTAX INTEGER {
        not-available(1),
        not-present(2),
        present(3)
    }
    MAX-ACCESS read-only
    STATUS current
    DESCRIPTION
    "Ribbon cartridge hardware is installed."
    ::= { zbrFeature 5 }

zbrFeatureLock OBJECT-TYPE
    SYNTAX INTEGER {
        not-available(1),
        not-present(2),
        present(3)
    }
    MAX-ACCESS read-only
    STATUS current
    DESCRIPTION
    "Lock hardware is installed."
    ::= { zbrFeature 6 }

zbrFeatureApplicator OBJECT-TYPE
    SYNTAX INTEGER {
        not-available(1),
        not-present(2),
        present(3)
    }
    MAX-ACCESS read-only
    STATUS current
    DESCRIPTION
    "Applicator hardware is installed."
    ::= { zbrFeature 7 }
    
zbrFeatureLights OBJECT-TYPE
    SYNTAX INTEGER {
        not-available(1),
        not-present(2),
        present(3)
    }
    MAX-ACCESS read-only
    STATUS current
    DESCRIPTION
    "Lights hardware is installed."
    ::= { zbrFeature 8 }
    
zbrFeatureHeadElementTestAvailability OBJECT-TYPE
    SYNTAX DisplayString (SIZE (0..20))
    MAX-ACCESS read-only
    STATUS current
    DESCRIPTION
    "Head Element Test Feature Availability."
    ::= { zbrFeature 9 }

zbrFeatureElevenAC OBJECT-TYPE
    SYNTAX INTEGER {
        not-available(1),
        not-present(2),
        present(3)
    }
    MAX-ACCESS read-only
    STATUS current
    DESCRIPTION
    "802.11AC radio is installed."
    ::= { zbrFeature 10 }

zbrFeatureBattery OBJECT-TYPE
    SYNTAX INTEGER {
        not-available(1),
        not-present(2),
        present(3)
    }
    MAX-ACCESS read-only
    STATUS current
    DESCRIPTION
    "Battery Feature Support."
    ::= { zbrFeature 11 }

zbrFeatureElevenAX OBJECT-TYPE
    SYNTAX INTEGER {
        not-available(1),
        not-present(2),
        present(3)
    }
    MAX-ACCESS read-only
    STATUS current
    DESCRIPTION
    "802.11AX radio is installed."
    ::= { zbrFeature 12 }
    
--===========================
-- zebra.zbrDevice.zbrAlerts
--===========================

zbrAlertsDisplay OBJECT-TYPE
   SYNTAX DisplayString (SIZE (0..100))
   MAX-ACCESS read-write
   STATUS current
   DESCRIPTION
   "Control of alerts displayed on front panel."
   ::= { zbrAlerts 1 }
   

zbrAlertsAudible OBJECT-TYPE
   SYNTAX OCTET STRING (SIZE (0..1024))
   MAX-ACCESS read-write
   STATUS current
   DESCRIPTION
   "Configure Audible Alerts"
   ::= { zbrAlerts 2 }

--===========================
-- Contunuation of zebra.zbrDevice
--===========================

zbrDeviceConfigurationNumber OBJECT-TYPE
   SYNTAX DisplayString (SIZE (0..100))
   MAX-ACCESS read-only
   STATUS current
   DESCRIPTION
   "Product Configuration Number."
   ::= { zbrDevice 14 }

zbrDeviceJobsPrint OBJECT-TYPE
   SYNTAX DisplayString (SIZE (0..20))
   MAX-ACCESS read-only
   STATUS current
   DESCRIPTION
   "Reports the number of jobs in the print queue."
   ::= { zbrDevice 16 }
    
zbrDeviceCurrentConfigurationNumber OBJECT-TYPE
   SYNTAX DisplayString (SIZE (0..100))
   MAX-ACCESS read-only
   STATUS current
   DESCRIPTION
   "Current Product Configuration Number."
   ::= { zbrDevice 18 }

--===========================
-- zebra.zbrDevice.zbrMcu
--===========================

zbrPmcuRevision OBJECT-TYPE
   SYNTAX DisplayString (SIZE (0..3))
   MAX-ACCESS read-only
   STATUS current
   DESCRIPTION
   "PMCU Revision Number."
   ::= { zbrMcu 1 }
   

zbrPmcuDesiredRevision OBJECT-TYPE
   SYNTAX DisplayString (SIZE (0..3))
   MAX-ACCESS read-only
   STATUS current
   DESCRIPTION
   "PMCU Desired Revision Number from last download containing PMCU firmware"
   ::= { zbrMcu 2 }

--===========================
-- zebra.zbrDevice.zbrMcuComm
--===========================

zbrMcuCommRevision OBJECT-TYPE
   SYNTAX DisplayString (SIZE (0..3))
   MAX-ACCESS read-only
   STATUS current
   DESCRIPTION
   "Communication MCU Revision Number."
   ::= { zbrMcuComm 1 }

zbrMcuCommDesiredRevision OBJECT-TYPE
   SYNTAX DisplayString (SIZE (0..3))
   MAX-ACCESS read-only
   STATUS current
   DESCRIPTION
   "Communication MCU Desired Revision Number from last download containing MCU firmware"
   ::= { zbrMcuComm 2 }
   
--===========================
-- zebra.zbrDevice.zbrMcuIoExpander
--===========================

zbrMcuIoExpanderRevision OBJECT-TYPE
   SYNTAX DisplayString (SIZE (0..3))
   MAX-ACCESS read-only
   STATUS current
   DESCRIPTION
   "IO Expander MCU Revision Number."
   ::= { zbrMcuIoExpander 1 }

zbrMcuIoExpanderDesiredRevision OBJECT-TYPE
   SYNTAX DisplayString (SIZE (0..3))
   MAX-ACCESS read-only
   STATUS current
   DESCRIPTION
   "IO Expander MCU Desired Revision Number from last download containing MCU firmware"
   ::= { zbrMcuIoExpander 2 }

--===========================
-- zebra.zbrDevice.zbrPrinthead
--===========================

zbrOdometerPrinthead OBJECT-TYPE
   SYNTAX INTEGER
   MAX-ACCESS read-only
   STATUS current
   DESCRIPTION
   "The total number of dots printed over the life of the printhead."
   ::= { zbrPrinthead 1 }

--===========================
-- zebra.zbrDevice.zbrPrinthead.zbrPrintheadTest
--===========================

zbrPrintheadTestSummary OBJECT-TYPE
   SYNTAX DisplayString
   MAX-ACCESS read-only
   STATUS current
   DESCRIPTION
   "Printhead test element summary.  String form A,B,C,D,E.
A is a number Element Failure
B is ether M (for Manual) or A (for Automatic)
C is the first test element
D is the last test element
E is the failure count"
   ::= { zbrPrintheadTest 1 }

--===========================
-- zebra.zbrDevice.zbApplicator
--===========================

zbrStartPrint OBJECT-TYPE
   SYNTAX INTEGER {
      low(1),
      high(2)
    }
   MAX-ACCESS read-write
   STATUS current
   DESCRIPTION
   "Select whether applicator START PRINT signal is active high or active low."
   ::= { zbrApplicator 1 }
  
zbrFeed OBJECT-TYPE
   SYNTAX INTEGER {
      low(1),
      high(2)
    }
   MAX-ACCESS read-write
   STATUS current
   DESCRIPTION
   "Select whether applicator FEED signal is active high or active low."
   ::= { zbrApplicator 2 }

zbrPause OBJECT-TYPE
   SYNTAX INTEGER {
      low(1),
      high(2)
    }
   MAX-ACCESS read-write
   STATUS current
   DESCRIPTION
   "Select whether applicator PAUSE signal is active high or active low."
   ::= { zbrApplicator 3 }
   
zbrReprint OBJECT-TYPE
   SYNTAX INTEGER {
      low(1),
      high(2)
    }
   MAX-ACCESS read-write
   STATUS current
   DESCRIPTION
   "Select whether applicator REPRINT signal is active high or active low."
   ::= { zbrApplicator 4 }
   
zbrServiceRequired OBJECT-TYPE
   SYNTAX INTEGER {
      low(1),
      high(2)
    }
   MAX-ACCESS read-write
   STATUS current
   DESCRIPTION
   "Select whether applicator SERVICE REQUIRED signal is active high or active low."
   ::= { zbrApplicator 5 }
   
zbrMediaOut OBJECT-TYPE
   SYNTAX INTEGER {
      low(1),
      high(2)
    }
   MAX-ACCESS read-write
   STATUS current
   DESCRIPTION
   "Select whether applicator MEDIA OUT signal is active high or active low."
   ::= { zbrApplicator 6 }

zbrRibbonOut OBJECT-TYPE
   SYNTAX INTEGER {
      low(1),
      high(2)
    }
   MAX-ACCESS read-write
   STATUS current
   DESCRIPTION
   "Select whether applicator RIBBON OUT signal is active high or active low."
   ::= { zbrApplicator 7 }

zbrDataReady OBJECT-TYPE
   SYNTAX INTEGER {
      low(1),
      high(2)
    }
   MAX-ACCESS read-write
   STATUS current
   DESCRIPTION
   "Select whether applicator DATA READY signal is active high or active low."
   ::= { zbrApplicator 8 }

zbrRfidVoid OBJECT-TYPE
   SYNTAX INTEGER {
      low(1),
      high(2)
    }
   MAX-ACCESS read-write
   STATUS current
   DESCRIPTION
   "Select whether applicator RFID VOID/SPARE signal is active high or active low."
   ::= { zbrApplicator 9 }

zbrRibbonLow OBJECT-TYPE
   SYNTAX INTEGER {
      low(1),
      high(2)
    }
   MAX-ACCESS read-write
   STATUS current
   DESCRIPTION
   "Select whether applicator RIBBON LOW signal is active high or active low."
   ::= { zbrApplicator 10 }
   
zbrVoltage OBJECT-TYPE
  SYNTAX INTEGER {
      voltage-off(1),
      voltage-5(2),
      voltage-24(3)
    }
   MAX-ACCESS read-write
   STATUS current
   DESCRIPTION
   "Select whether applicator output voltage is off, 5V, or 24V."
   ::= { zbrApplicator 11 }
   
zbrErrorOnPause OBJECT-TYPE
  SYNTAX INTEGER {
      enabled(1),
      disabled(2)
    }
   MAX-ACCESS read-write
   STATUS current
   DESCRIPTION
   "Select whether Error on Pause is disabled or enabled."
   ::= { zbrApplicator 12 }

zbrEndPrint OBJECT-TYPE
  SYNTAX INTEGER {
      off(1),
      mode-1(2),
      mode-2(3),
      mode-3(4),
      mode-4(5)
    }
   MAX-ACCESS read-write
   STATUS current
   DESCRIPTION
   "Select applicator port END PRINT mode of operation."
   ::= { zbrApplicator 13 }
   
zbrStartPrintMode OBJECT-TYPE
  SYNTAX INTEGER {
      pulse(1),
      level(2)
    }
   MAX-ACCESS read-write
   STATUS current
   DESCRIPTION
   "Select applicator port START PRINT mode of operation (level or pulse)."
   ::= { zbrApplicator 14 }
   
zbrDataReadyActivation OBJECT-TYPE
  SYNTAX INTEGER {
      format(1),
      print(2)
    }
   MAX-ACCESS read-write
   STATUS current
   DESCRIPTION
   "Select whether applicator port DATA READY signal is asserted for all formats, or printing formats only."
   ::= { zbrApplicator 15 }
   
--===========================
-- zebra.zbrTrackedAlertsTable
--===========================
zbrTrackedAlertsTable OBJECT-TYPE
   SYNTAX  SEQUENCE OF ZbrTrackedAlertsTableEntry
   MAX-ACCESS  not-accessible
   STATUS  current
   DESCRIPTION "Tracked Alerts Table."
   ::= { zbrDevice 31 }

zbrTrackedAlertsTableEntry OBJECT-TYPE
   SYNTAX  ZbrTrackedAlertsTableEntry
   MAX-ACCESS  not-accessible
   STATUS  current
   DESCRIPTION "Tracked Alert Table Entry."
   INDEX { zbrTrackedAlertsIndex }
   ::= { zbrTrackedAlertsTable 1 }

ZbrTrackedAlertsTableEntry ::= SEQUENCE {
      zbrTrackedAlertsIndex         INTEGER,
      zbrTrackedAlertsSeverity      INTEGER,
      zbrTrackedAlertsTrainingLevel INTEGER,
      zbrTrackedAlertsGroup         INTEGER,
      zbrTrackedAlertsCode          INTEGER,
      zbrTrackedAlertsTime          TimeTicks
    }

zbrTrackedAlertsIndex OBJECT-TYPE
    SYNTAX INTEGER (0..50)
    MAX-ACCESS read-only
    STATUS current
    DESCRIPTION "The index of Tracked Alert entries (0-50)"
    ::= { zbrTrackedAlertsTableEntry 1 }

zbrTrackedAlertsSeverity OBJECT-TYPE
    SYNTAX INTEGER {
         other(1),
         critical(3),
         warning(4)
      }
    MAX-ACCESS read-only
    STATUS current
    DESCRIPTION
      "The level of severity of this alert table entry.  The printer determines the severity
       level assigned to each entry into the table using these values:
       other(1), critical(3), warning(4)"
    ::= { zbrTrackedAlertsTableEntry 2 }

zbrTrackedAlertsTrainingLevel OBJECT-TYPE
   SYNTAX INTEGER {
      other(1),
      unknown(2),
      untrained(3),
      trained(4),
      fieldService(5),
      management(6)
   }
   MAX-ACCESS read-only
   STATUS current
   DESCRIPTION  "The level of training required to handle the alert"
   ::= { zbrTrackedAlertsTableEntry 3 }

zbrTrackedAlertsGroup  OBJECT-TYPE
   SYNTAX INTEGER {
      system(1),
      media(2),
      ribbon(3),
      printhead(4),
      rewinder(5),
      cutter(6),
      zbi(7),
      battery(8),
      rfid(9)
   }
   MAX-ACCESS read-only
   STATUS current
   DESCRIPTION  "The printer subsytem within the printer that the alert is associated with."
   ::= { zbrTrackedAlertsTableEntry 4 }

zbrTrackedAlertsCode OBJECT-TYPE
   SYNTAX INTEGER {
      paper-out(1),
      ribbon-out(2),
      head-too-hot(3),
      head-under-temp(4),
      head-open(5),
      power-supply-over-temp(6),
      motor-over-temp(7),
      ribbon-in(8),
      rewind-fault(9),
      cutter-jammed(10),
      printer-paused(11),
      head-element-bad(12),
      basic-runtime(13),
      basic-forced(14),
      power-on(15),
      battery-low(16),
      rfid-error(17),
      cold-start(18),
      ribbon-auth-error(19),
      clean-cutter(20),
      paper-error(21)
   }
   MAX-ACCESS read-only
   STATUS current
   DESCRIPTION  "The Alert Conditions, including these conditions."
   ::= { zbrTrackedAlertsTableEntry 5 }

zbrTrackedAlertsTime  OBJECT-TYPE
   SYNTAX TimeTicks
   MAX-ACCESS read-only
   STATUS current
   DESCRIPTION  "The value of sysUpTime (1.3.6.1.2.1.1.3.0) at the time that this alert was generated."
   ::= { zbrTrackedAlertsTableEntry 6 }

--===========================
-- zebra.zbrDevice.zbrFips
--===========================

zbrFipsEnabled OBJECT-TYPE
   SYNTAX INTEGER {
      yes(1),
      no(2)
    }
   MAX-ACCESS read-write
   STATUS current
   DESCRIPTION
   "Select whether you want FIPS enabled or not."
   ::= { zbrFips 1 }
   
zbrFipsReport OBJECT-TYPE
   SYNTAX INTEGER {
      valid(1),
      not-valid(2)
    }
   MAX-ACCESS read-only
   STATUS current
   DESCRIPTION
   "Checks to see if FIPS is validated."
   ::= { zbrFips 2 }
--===========================
-- zebra.zbrSensor
--===========================

zbrSensorPeelBrightness OBJECT-TYPE
    SYNTAX INTEGER
    MAX-ACCESS read-only
    STATUS current
    DESCRIPTION
    "Peeler Sensor Brightness level"
    ::= { zbrSensorPeel 1 }

zbrSensorPeelGain OBJECT-TYPE
    SYNTAX INTEGER
    MAX-ACCESS read-only
    STATUS current
    DESCRIPTION
    "Peeler Sensor gain level"
    ::= { zbrSensorPeel 2 }

zbrSensorPeelThreshold OBJECT-TYPE
    SYNTAX INTEGER
    MAX-ACCESS read-only
    STATUS current
    DESCRIPTION
    "Peeler Sensor threshold level"
    ::= { zbrSensorPeel 3 }

zbrSensorPeelCurrent OBJECT-TYPE
    SYNTAX INTEGER
    MAX-ACCESS read-only
    STATUS current
    DESCRIPTION
    "Peeler Sensor current value"
    ::= { zbrSensorPeel 4 }

zbrSensorWidthCurrent OBJECT-TYPE
   SYNTAX INTEGER
    MAX-ACCESS read-only
    STATUS current
    DESCRIPTION
    "Width Sensor current width"
    ::= { zbrSensorWidth 1 }
    
zbrSensorWidthInDots OBJECT-TYPE
   SYNTAX INTEGER
    MAX-ACCESS read-only
    STATUS current
    DESCRIPTION
    "Width Sensor current width in dots"
    ::= { zbrSensorWidth 2 }

zbrSensorGapBrightness OBJECT-TYPE
    SYNTAX INTEGER
    MAX-ACCESS read-only
    STATUS current
    DESCRIPTION
    "Gap Sensor Brightness level"
    ::= { zbrSensorGap 1 }

zbrSensorGapGain OBJECT-TYPE
    SYNTAX INTEGER
    MAX-ACCESS read-only
    STATUS current
    DESCRIPTION
    "Gap Sensor gain level"
    ::= { zbrSensorGap 2 }

zbrSensorGapOffset OBJECT-TYPE
    SYNTAX INTEGER
    MAX-ACCESS read-only
    STATUS current
    DESCRIPTION
    "Gap Sensor offset level"
    ::= { zbrSensorGap 3 }

zbrSensorGapThreshold OBJECT-TYPE
    SYNTAX INTEGER
    MAX-ACCESS read-only
    STATUS current
    DESCRIPTION
    "Gap Sensor threshold value"
    ::= { zbrSensorGap 4 }

zbrSensorGapCurrent OBJECT-TYPE
    SYNTAX INTEGER
    MAX-ACCESS read-only
    STATUS current
    DESCRIPTION
    "Gap Sensor current value"
    ::= { zbrSensorGap 5 }

zbrSensorGapPaperOutThreshold OBJECT-TYPE
    SYNTAX INTEGER
    MAX-ACCESS read-only
    STATUS current
    DESCRIPTION
    "Gap Sensor threshold value"
    ::= { zbrSensorGap 6 }    

zbrSensorBackBarBrightness OBJECT-TYPE
    SYNTAX INTEGER
    MAX-ACCESS read-only
    STATUS current
    DESCRIPTION
    "Back Bar Sensor Brightness level"
    ::= { zbrSensorBackBar 1 }

zbrSensorBackBarGain OBJECT-TYPE
    SYNTAX INTEGER
    MAX-ACCESS read-only
    STATUS current
    DESCRIPTION
    "Back Bar Sensor gain level"
    ::= { zbrSensorBackBar 2 }

zbrSensorBackBarOffset OBJECT-TYPE
    SYNTAX INTEGER
    MAX-ACCESS read-only
    STATUS current
    DESCRIPTION
    "Back Bar Sensor offset level"
    ::= { zbrSensorBackBar 3 }

zbrSensorBackBarThreshold OBJECT-TYPE
    SYNTAX INTEGER
    MAX-ACCESS read-only
    STATUS current
    DESCRIPTION
    "Back Bar Sensor threshold value"
    ::= { zbrSensorBackBar 4 }

zbrSensorBackBarCurrent OBJECT-TYPE
    SYNTAX INTEGER
    MAX-ACCESS read-only
    STATUS current
    DESCRIPTION
    "Back Bar Sensor current value"
    ::= { zbrSensorBackBar 5 }

zbrSensorBackBarPaperOutThreshold OBJECT-TYPE
    SYNTAX INTEGER
    MAX-ACCESS read-only
    STATUS current
    DESCRIPTION
    "Back Bar Sensor threshold value"
    ::= { zbrSensorBackBar 6 }

zbrSensorFrontBarBrightness OBJECT-TYPE
    SYNTAX INTEGER
    MAX-ACCESS read-only
    STATUS current
    DESCRIPTION
    "Front Bar Sensor Brightness level"
    ::= { zbrSensorFrontBar 1 }

zbrSensorFrontBarGain OBJECT-TYPE
    SYNTAX INTEGER
    MAX-ACCESS read-only
    STATUS current
    DESCRIPTION
    "Front Bar Sensor gain level"
    ::= { zbrSensorFrontBar 2 }

zbrSensorFrontBarOffset OBJECT-TYPE
    SYNTAX INTEGER
    MAX-ACCESS read-only
    STATUS current
    DESCRIPTION
    "Front Bar Sensor offset level"
    ::= { zbrSensorFrontBar 3 }

zbrSensorFrontBarThreshold OBJECT-TYPE
    SYNTAX INTEGER
    MAX-ACCESS read-only
    STATUS current
    DESCRIPTION
    "Front Bar Sensor threshold value"
    ::= { zbrSensorFrontBar 4 }

zbrSensorFrontBarCurrent OBJECT-TYPE
    SYNTAX INTEGER
    MAX-ACCESS read-only
    STATUS current
    DESCRIPTION
    "Front Bar Sensor current value"
    ::= { zbrSensorFrontBar 5 }

zbrSensorFrontBarPaperOutThreshold OBJECT-TYPE
    SYNTAX INTEGER
    MAX-ACCESS read-only
    STATUS current
    DESCRIPTION
    "Front Bar Sensor threshold value"
    ::= { zbrSensorFrontBar 6 }

zbrSensorHeadTemperature OBJECT-TYPE
    SYNTAX INTEGER
    MAX-ACCESS read-only
    STATUS current
    DESCRIPTION
    "Print Head Temperature Sensor value"
    ::= { zbrSensorHead 1 }

zbrSensorHeadTemperatureCelsius OBJECT-TYPE
    SYNTAX INTEGER
    MAX-ACCESS read-only
    STATUS current
    DESCRIPTION
    "Print Head Temperature Sensor value in Celsius"
    ::= { zbrSensorHead 2 }

zbrSensorHeadTemperatureAverageInCelsius OBJECT-TYPE
    SYNTAX INTEGER
    MAX-ACCESS read-only
    STATUS current
    DESCRIPTION
    "Average Print Head Temperature value in Celsius"
    ::= { zbrSensorHead 3 }   
    
zbrSensorHeadElementTest OBJECT-TYPE
   SYNTAX DisplayString
   MAX-ACCESS read-write
   STATUS current
   DESCRIPTION
   "Execute head element test"
   ::= { zbrSensorHead 4 }     

zbrSensorBatteryAverageCurrentInMA OBJECT-TYPE
    SYNTAX INTEGER
    MAX-ACCESS read-only
    STATUS current
    DESCRIPTION
    "Battery average current reading in mA"
    ::= { zbrSensorBattery 1 }

zbrSensorBatteryInVolts OBJECT-TYPE
    SYNTAX DisplayString
    MAX-ACCESS read-only
    STATUS current
    DESCRIPTION
    "Battery Voltage reading"
    ::= { zbrSensorBattery 2 }

zbrSensorBatteryAverageADC OBJECT-TYPE
    SYNTAX INTEGER
    MAX-ACCESS read-only
    STATUS current
    DESCRIPTION
    "Average Battery ADC reading"
    ::= { zbrSensorBattery 3 }
    
zbrSensorAmbientTemperatureCurrentReading OBJECT-TYPE
   SYNTAX DisplayString (SIZE (0..3))
   MAX-ACCESS read-only
   STATUS current
   DESCRIPTION
   "Current ambient temperature reading from the IoT Sensors card - floating point number in celsius from -40.0 to 125.0 degrees celsius."
   ::= { zbrSensorAmbientTemp 1 }      
   
zbrSensorAmbientHumidityCurrentReading OBJECT-TYPE
   SYNTAX DisplayString (SIZE (0..3))
   MAX-ACCESS read-only
   STATUS current
   DESCRIPTION
   "Current ambient humidity reading from the IoT Sensors card - floating point number represented as a percentage."
   ::= { zbrSensorAmbientHumidity 1 }    

zbrSensorProximityCurrentReading OBJECT-TYPE
   SYNTAX INTEGER
   MAX-ACCESS read-only
   STATUS current
   DESCRIPTION
   "Current proximity sensor reading from the IoT Sensors card - integer from 0 to 4095."
   ::= { zbrSensorProximity 1 }      
   
zbrSensorAmbientLightCurrentReading OBJECT-TYPE
   SYNTAX INTEGER
   MAX-ACCESS read-only
   STATUS current
   DESCRIPTION
   "Current ambient light from the IoT Sensors card - integer number expressed in lux."
   ::= { zbrSensorAmbientLight 1 }    

zbrSensorAirPressureCurrentReading OBJECT-TYPE
    SYNTAX DisplayString (SIZE (0..6))
    MAX-ACCESS read-only
    STATUS current
    DESCRIPTION
    "Air pressure in millibars"
    ::= { zbrSensorAirPressure 1 }
    
zbrSensorMagnetometerCurrentReading OBJECT-TYPE
    SYNTAX DisplayString (SIZE (0..32))
    MAX-ACCESS read-only
    STATUS current
    DESCRIPTION
    "magnetic field in [x,y,x] Gauss"
    ::= { zbrSensorMagnetometer 1 }
    
zbrSensorObjectTemperatureCurrentReading OBJECT-TYPE
    SYNTAX DisplayString (SIZE (0..6))
    MAX-ACCESS read-only
    STATUS current
    DESCRIPTION
    "Object Temperature in degrees Celsius"
    ::= { zbrSensorObjectTemperature 1 }
    
--===========================
-- zebra.zbrDevice.zbrSerialNumbers
--===========================

zbrSerialNumberMlb OBJECT-TYPE
   SYNTAX DisplayString
   MAX-ACCESS read-only
   STATUS current
   DESCRIPTION
   "MLB (Main Logic Board) Serial Number."
   ::= { zbrSerialNumbers 1 }

zbrSerialNumberMlbDate OBJECT-TYPE
   SYNTAX DisplayString
   MAX-ACCESS read-only
   STATUS current
   DESCRIPTION
   "Manufacture date of the MLB (Main Logic Board)."
   ::= { zbrSerialNumbers 2 }

zbrSerialNumberControlPanel OBJECT-TYPE
   SYNTAX DisplayString
   MAX-ACCESS read-only
   STATUS current
   DESCRIPTION
   "Control Panel (aka Front Panel aka User Interface) Serial Number."
   ::= { zbrSerialNumbers 3 }

zbrSerialNumberControlPanelDate OBJECT-TYPE
   SYNTAX DisplayString
   MAX-ACCESS read-only
   STATUS current
   DESCRIPTION
   "Manufacture date of the Control Panel (aka Front Panel aka User Interface)."
   ::= { zbrSerialNumbers 4 }

zbrSerialNumberOptionBoard OBJECT-TYPE
   SYNTAX DisplayString
   MAX-ACCESS read-only
   STATUS current
   DESCRIPTION
   "Option Board Serial Number."
   ::= { zbrSerialNumbers 5 }

zbrSerialNumberOptionBoardDate OBJECT-TYPE
   SYNTAX DisplayString
   MAX-ACCESS read-only
   STATUS current
   DESCRIPTION
   "Option Board Manufacture date."
   ::= { zbrSerialNumbers 6 }



zbrSerialNumberWlanOptionBoard OBJECT-TYPE
   SYNTAX DisplayString
   MAX-ACCESS read-only
   STATUS current
   DESCRIPTION
   "Serial number of the wlan option board."
   ::= { zbrSerialNumbers 9 }

zbrSerialNumberWlanOptionBoardDate OBJECT-TYPE
   SYNTAX DisplayString
   MAX-ACCESS read-only
   STATUS current
   DESCRIPTION
   "Manufacture date of the wlan option board."
   ::= { zbrSerialNumbers 10 }

zbrSerialNumberApplicatorOptionBoard OBJECT-TYPE
   SYNTAX DisplayString
   MAX-ACCESS read-only
   STATUS current
   DESCRIPTION
   "Serial number of the applicator option board."
   ::= { zbrSerialNumbers 11 }

zbrSerialNumberApplicatorOptionBoardDate OBJECT-TYPE
   SYNTAX DisplayString
   MAX-ACCESS read-only
   STATUS current
   DESCRIPTION
   "Manufacture date of the applicator option board."
   ::= { zbrSerialNumbers 12 }

zbrSerialNumberPrinthead OBJECT-TYPE
   SYNTAX DisplayString
   MAX-ACCESS read-only
   STATUS current
   DESCRIPTION
   "Serial number of the printhead."
   ::= { zbrSerialNumbers 13 }

zbrSerialNumberPrintheadDate OBJECT-TYPE
   SYNTAX DisplayString
   MAX-ACCESS read-only
   STATUS current
   DESCRIPTION
   "Manufacture date of the printhead."
   ::= { zbrSerialNumbers 14 }

zbrSerialNumberParallelOptionBoard OBJECT-TYPE
   SYNTAX DisplayString
   MAX-ACCESS read-only
   STATUS current
   DESCRIPTION
   "Serial number of the parallel option board."
   ::= { zbrSerialNumbers 15 }

zbrSerialNumberParallelOptionBoardDate OBJECT-TYPE
   SYNTAX DisplayString
   MAX-ACCESS read-only
   STATUS current
   DESCRIPTION
   "Manufacture date of the parallel option board."
   ::= { zbrSerialNumbers 16 }

zbrSerialNumberUsbHostOptionBoard OBJECT-TYPE
   SYNTAX DisplayString
   MAX-ACCESS read-only
   STATUS current
   DESCRIPTION
   "Serial number of the usb_host option board."
   ::= { zbrSerialNumbers 17 }

zbrSerialNumberUsbHostOptionBoardDate OBJECT-TYPE
   SYNTAX DisplayString
   MAX-ACCESS read-only
   STATUS current
   DESCRIPTION
   "Manufacture date of the usb_host option board."
   ::= { zbrSerialNumbers 18 }

zbrSerialNumberWiredEthernetOptionBoard OBJECT-TYPE
   SYNTAX DisplayString
   MAX-ACCESS read-only
   STATUS current
   DESCRIPTION
   "Serial number of the wired_ethernet option board."
   ::= { zbrSerialNumbers 19 }

zbrSerialNumberWiredEthernetOptionBoardDate OBJECT-TYPE
   SYNTAX DisplayString
   MAX-ACCESS read-only
   STATUS current
   DESCRIPTION
   "Manufacture date of the wired_ethernet option board."
   ::= { zbrSerialNumbers 20 }

--===========================
-- Another continuation of zebra.zbrDevice
--===========================
zbrDeviceLocked OBJECT-TYPE
   SYNTAX INTEGER {
      no(1),
      yes(2)
    }
   MAX-ACCESS read-only
   STATUS current
   DESCRIPTION
   "Media lock is locked or not"
   ::= { zbrDevice 20 }
   
zbrDeviceSetClockToBuildDate OBJECT-TYPE
   SYNTAX INTEGER {
      enabled(1),
      disabled(2)
   }
   MAX-ACCESS read-write
   STATUS current
   DESCRIPTION
    "Enable or disable lower bound of rtc.date based on firmware build date."
   ::= { zbrDevice 21 }
   
zbrDeviceResetButtonEnable OBJECT-TYPE
   SYNTAX INTEGER {
      on(1),
      off(2)
    }
   MAX-ACCESS read-write
   STATUS current
   DESCRIPTION
   "Enable[on] or Disable[off] the reset button."
   ::= { zbrDevice 32 }
   
zbrDeviceZuid OBJECT-TYPE
   SYNTAX DisplayString
   MAX-ACCESS read-only
   STATUS current
   DESCRIPTION
   "unique Id for the printer used for MQTT ClientId, combination of manufacturing programmed serial number, CPU Id and MLB crypto chip serial number (if applicable)."
   ::= { zbrDevice 34 }
   
--===========================
-- zebra.zbrInterfaces.zbrComm
--===========================

zbrCommBaud OBJECT-TYPE
   SYNTAX INTEGER (4800..115200)
   MAX-ACCESS read-write
   STATUS current
   DESCRIPTION
   "The printer's serial port baud rate - one of
   (4800,9600,14400,19200,28800,38400,57600,115200)."
   ::= { zbrComm 1 }

zbrCommDataBits OBJECT-TYPE
   SYNTAX INTEGER (7..8)
   MAX-ACCESS read-write
   STATUS current
   DESCRIPTION
   "Number of data bits."
   ::= { zbrComm 2 }

zbrCommParity OBJECT-TYPE
    SYNTAX INTEGER {
        none(1),
        odd(2),
        even(3)
    }
   MAX-ACCESS read-write
   STATUS current
   DESCRIPTION
   "Com port parity."
   ::= { zbrComm 3 }

zbrCommStopBits OBJECT-TYPE
   SYNTAX INTEGER (1..2)
   MAX-ACCESS read-write
   STATUS current
   DESCRIPTION
   "Com port stop bits."
   ::= { zbrComm 4 }

zbrCommDsr OBJECT-TYPE
   SYNTAX INTEGER {
        on(1),
        off(2)
    }
   MAX-ACCESS read-only
   STATUS current
   DESCRIPTION
   "DSR control."
   ::= { zbrComm 5 }

zbrCommHostHandshake OBJECT-TYPE
    SYNTAX INTEGER {
        xon-xoff(1),
        rts-cts(2)
    }
    MAX-ACCESS read-write
    STATUS current
    DESCRIPTION
    "Ser1 Host Handshake"
    ::= { zbrComm 6 }

zbrCommHalt OBJECT-TYPE
   SYNTAX INTEGER {
      no(1),
      yes(2)
    }
    MAX-ACCESS read-write
    STATUS current
    DESCRIPTION
    "Comm port is halted on error."
    ::= { zbrComm 7 }

zbrCommType OBJECT-TYPE
    SYNTAX INTEGER {
        dte(1),
        dce(2),
        auto(3)
    }
   MAX-ACCESS read-write
   STATUS current
   DESCRIPTION
   "This parameter refers to the serial type communication."
   ::= { zbrComm 8 }

zbrCommMode OBJECT-TYPE
    SYNTAX INTEGER {
        rs232(1),
        rs422-rs485(2),
        rs485-multidrop(3)
    }
    MAX-ACCESS read-write
    STATUS current
    DESCRIPTION
    "This parameter refers to the serial mode."
    ::= { zbrComm 9 }

--===========================
-- zebra.zbrInterfaces.zbrBluetooth
--===========================

zbrBluetoothDiscoverable OBJECT-TYPE
   SYNTAX INTEGER {
        on(1),
        off(2)
    }
   MAX-ACCESS read-write
   STATUS current
   DESCRIPTION
   "Enable or disable the Bluetooth discoverable mode."
   ::= { zbrBluetooth 3 }

zbrBluetoothFriendlyName OBJECT-TYPE
   SYNTAX DisplayString (SIZE (0..17))
   MAX-ACCESS read-write
   STATUS current
   DESCRIPTION
   "The friendly name, which is used during service discovery."
   ::= { zbrBluetooth 5 }

zbrBluetoothVersion OBJECT-TYPE
   SYNTAX DisplayString (SIZE (0..100))
   MAX-ACCESS read-only
   STATUS current
   DESCRIPTION
   "Bluetooth library version number."
   ::= { zbrBluetooth 6 }

zbrBluetoothDate OBJECT-TYPE
   SYNTAX DisplayString (SIZE (0..100))
   MAX-ACCESS read-only
   STATUS current
   DESCRIPTION
   "Release date of the bluetooth module."
   ::= { zbrBluetooth 7 }

zbrBluetoothLocalName OBJECT-TYPE
   SYNTAX DisplayString (SIZE (0..30))
   MAX-ACCESS read-only
   STATUS current
   DESCRIPTION
   "The local name, which is used during service discovery."
   ::= { zbrBluetooth 10 }

zbrBluetoothAddress OBJECT-TYPE
   SYNTAX DisplayString (SIZE (0..30))
   MAX-ACCESS read-only
   STATUS current
   DESCRIPTION
   "The MAC address."
   ::= { zbrBluetooth 11 }

zbrBluetoothBluetoothPin OBJECT-TYPE
   SYNTAX DisplayString (SIZE (0..30))
   MAX-ACCESS read-write
   STATUS current
   DESCRIPTION
   "Bluetooth pin, used to connect to the printer only when the command
    bluetooth.authentication is set to 'setpin'."
   ::= { zbrBluetooth 12 }

zbrBluetoothShortAddress OBJECT-TYPE
   SYNTAX DisplayString (SIZE (0..30))
   MAX-ACCESS read-only
   STATUS current
   DESCRIPTION
   "The MAC address with the colon characters removed. "
   ::= { zbrBluetooth 13 }

zbrBluetoothRadioVersion OBJECT-TYPE
   SYNTAX DisplayString (SIZE (0..100))
   MAX-ACCESS read-only
   STATUS current
   DESCRIPTION
   "Version of the installed Bluetooth radio module."
   ::= { zbrBluetooth 14 }

-- zbrBluetoothAfhMode OBJECT-TYPE
--    ::= { zbrBluetooth 15 }
-- zbrBluetoothAfhMap OBJECT-TYPE
--    ::= { zbrBluetooth 16 }
-- zbrBluetoothAfhMapCurr OBJECT-TYPE
--    ::= { zbrBluetooth 17 }

zbrBluetoothEnable OBJECT-TYPE
   SYNTAX INTEGER {
        on(1),
        off(2)
    }
   MAX-ACCESS read-write
   STATUS current
   DESCRIPTION
   "Enable or disable the Bluetooth radio."
   ::= { zbrBluetooth 19 }

zbrBluetoothConnected OBJECT-TYPE
    SYNTAX INTEGER {
        yes(1),
        no(2)
    }
   MAX-ACCESS read-only
   STATUS current
   DESCRIPTION
   "Is there an Bluetooth connection."
   ::= { zbrBluetooth 21 }

zbrBluetoothConnectedSecurityMode OBJECT-TYPE
    SYNTAX DisplayString (SIZE (0..2))
    MAX-ACCESS read-only
    STATUS current
    DESCRIPTION
    "Bluetooth Connected Security Mode"
    ::= { zbrBluetooth 22 }

zbrBluetoothMinimumSecurityMode OBJECT-TYPE
    SYNTAX INTEGER (1..4)
    MAX-ACCESS read-write
    STATUS current
    DESCRIPTION
    "Bluetooth minimum security Mode"
    ::= { zbrBluetooth 23 }

zbrBluetoothBonding OBJECT-TYPE
   SYNTAX INTEGER {
        on(1),
        off(2)
    }
   MAX-ACCESS read-write
   STATUS current
   DESCRIPTION
   "Enable or disable the Bluetooth bonding"
   ::= { zbrBluetooth 24 }

zbrBluetoothClearBondingCache OBJECT-TYPE
   SYNTAX INTEGER {
        clear(1)
    }
   MAX-ACCESS read-write
   STATUS current
   DESCRIPTION
   "Remove all saved bonding keys immediately."
   ::= { zbrBluetooth 25 }

zbrBluetoothAllowNonDisplayNumComp OBJECT-TYPE
   SYNTAX INTEGER {
        off(1),
        print(2),
        noprint(3)
    }
   MAX-ACCESS read-write
   STATUS current
   DESCRIPTION
   "Off does not allow Passkey for non display printers, Print prints and accepts the Passkey for non display printers, No Print accepts but does not print the Passkey"
   ::= { zbrBluetooth 26 }

zbrBluetoothEnableReconnect OBJECT-TYPE
   SYNTAX INTEGER {
        off(1),
        iOS-only(2)
    }
   MAX-ACCESS read-write
   STATUS current
   DESCRIPTION
   "Off disable auto reconnect, iOS_only enable auto reconnect for iOS devices only"
   ::= { zbrBluetooth 27 }

zbrBluetoothInstalled OBJECT-TYPE
    SYNTAX DisplayString (SIZE (0..100))
    MAX-ACCESS read-only
    STATUS current
    DESCRIPTION
    "Is Bluetooth radio is installed?"
   ::= { zbrBluetooth 28 }
   
zbrBluetoothJsonConfigChannelEnable OBJECT-TYPE
   SYNTAX INTEGER {
      on(1),
      off(2)
    }
    MAX-ACCESS read-write
    STATUS current
    DESCRIPTION
    "Controls the presence of the json configuration channel over bluetooth.  
    In the 'off' state it is not advertised or available.  Changing the value to 'off' doesn't affect the current state (see note).  
    In the 'on' state the channel is available when the main SPP channel is connected.  It will then be advertised.  
    NOTE: The json config channel will stop being advertised when there is no connection to the json channel and there is no connection on the main SPP channel."
   ::= { zbrBluetooth 29 }

zbrBluetoothPageScanWindow OBJECT-TYPE
   SYNTAX INTEGER {
        scan-15(15),
        scan-60(60)
    }
    MAX-ACCESS read-write
    STATUS current
    DESCRIPTION
    "Page scan window timing"
   ::= { zbrBluetooth 30 }
   
zbrBluetoothPowerClass OBJECT-TYPE
   SYNTAX INTEGER (1..3)
   MAX-ACCESS read-write
   STATUS current
   DESCRIPTION
   "Configure the Max TX power based upon Class"
   ::= { zbrBluetooth 31 }
      
zbrBluetoothDisconnectIdleLink OBJECT-TYPE
   SYNTAX INTEGER {
     yes(1),
     no(2)
   }
   MAX-ACCESS read-write
   STATUS current
   DESCRIPTION
   "Close idle bluetooth connection with no active channels"
   ::= { zbrBluetooth 32 }

zbrBluetoothSniffModeEnable OBJECT-TYPE
   SYNTAX INTEGER {
     enabled(1),
     disabled(2)
   }
   MAX-ACCESS read-write
   STATUS current
   DESCRIPTION
   "Sniff mode reduces power for active connections with no data transfer"
   ::= { zbrBluetooth 33 }

--===========================
-- zebra.zbrInterfaces.zbrBluetooth.zbrBluetoothLowEnergy
--===========================

zbrBluetoothLeControllerMode OBJECT-TYPE
   SYNTAX INTEGER {
        both(1),
        classic(2),
        le(3)
    }
   MAX-ACCESS read-write
   STATUS current
   DESCRIPTION
   "Select Bluetooth controller mode for dual-mode (BR/EDR/LE) controllers."
   ::= { zbrBluetoothLowEnergy 2 }
   
zbrBluetoothLePowerClass OBJECT-TYPE
   SYNTAX INTEGER (1..3)
   MAX-ACCESS read-write
   STATUS current
   DESCRIPTION
   "Configure the BTLE Max TX power based upon Class"
   ::= { zbrBluetoothLowEnergy 4 }   


--===========================
--===========================
-- zebra.zbrInterfaces.zbrParallelPort
--===========================

zbrParallelPortPresent OBJECT-TYPE
    SYNTAX INTEGER {
        present(1),
        not-installed(2)
    }
    MAX-ACCESS read-only
    STATUS current
    DESCRIPTION
    "Report presence of parallel port"
    ::= { zbrParallelPort 1 }

zbrParallelPortMode OBJECT-TYPE
    SYNTAX INTEGER {
        bidirectional(1),
        unidirectional(2)
    }
    MAX-ACCESS read-write
    STATUS current
    DESCRIPTION
    "Parallel port mode, bidirectional or unidirectional"
    ::= { zbrParallelPort 2 }


--=================================================================================================
-- zebra.zbrInterfaces.zbrIfWirelessLan
--=================================================================================================
zbrWlanIpDnsDomainUserValue OBJECT-TYPE
   SYNTAX DisplayString
   MAX-ACCESS read-only
   STATUS current
   DESCRIPTION
   "This will display the value that the user has set to wlan.ip.dns.domain. Whether this value will be used will depend on the rules for wlan.ip.dns.domains."
   ::= { zbrIfWirelessLan 4 }
   
zbrWlanIpDnsServersUserValue OBJECT-TYPE
   SYNTAX DisplayString
   MAX-ACCESS read-only
   STATUS current
   DESCRIPTION
   "This will display the value that the user has set to wlan.ip.dns.servers. Whether this value will be used will depend on the rules for wlan.ip.dns.servers."
   ::= { zbrIfWirelessLan 5 }


--=================================================================================================
--=================================================================================================
-- zebra.zbrInterfaces.zbrIfWirelessLan.zbrWlanStatus
--=================================================================================================
zbrWLanStatusAssociated OBJECT-TYPE
   SYNTAX INTEGER {
        yes(1),
        no(2)
    }
   MAX-ACCESS read-only
   STATUS current
   DESCRIPTION
   "If the radio is associated."
   ::= { zbrWLanStatus 1 }

zbrWLanStatusSignalStrength OBJECT-TYPE
   SYNTAX INTEGER
   MAX-ACCESS read-only
   STATUS current
   DESCRIPTION
   "Signal strength of the wireless radio connection."
   ::= { zbrWLanStatus 2 }

zbrWLanStatusFirmwareVersion OBJECT-TYPE
   SYNTAX DisplayString
   MAX-ACCESS read-only
   STATUS current
   DESCRIPTION
   "Firmware version of the wireless radio."
   ::= { zbrWLanStatus 3 }

zbrWLanStatusMfgId OBJECT-TYPE
   SYNTAX DisplayString
   MAX-ACCESS read-only
   STATUS current
   DESCRIPTION
   "Manufacturer's ID of the wireless radio."
   ::= { zbrWLanStatus 4 }

zbrWLanStatusCurrentChannel OBJECT-TYPE
   SYNTAX INTEGER
   MAX-ACCESS read-only
   STATUS current
   DESCRIPTION
   "Current channel over which the wireless radio is connected."
   ::= { zbrWLanStatus 5 }

zbrWLanStatusLastTxRate OBJECT-TYPE
   SYNTAX INTEGER
   MAX-ACCESS read-only
   STATUS current
   DESCRIPTION
   "Rate at which the last packet was transmitted."
   ::= { zbrWLanStatus 6 }

zbrWLanStatusBssid OBJECT-TYPE
   SYNTAX PhysAddress
   MAX-ACCESS read-only
   STATUS current
   DESCRIPTION
   "BSSID to which the wireless radio is connected."
   ::= { zbrWLanStatus 7 }

zbrWLanStatusWpaVersion OBJECT-TYPE
   SYNTAX DisplayString
   MAX-ACCESS read-only
   STATUS current
   DESCRIPTION
   "Version of WPA that is in use."
   ::= { zbrWLanStatus 8 }

zbrWLanStatusWpaGroupwiseCipherSuite OBJECT-TYPE
   SYNTAX DisplayString
   MAX-ACCESS read-only
   STATUS current
   DESCRIPTION
   "Cipher suite being used for the WPA groupkey."
   ::= { zbrWLanStatus 9 }

zbrWLanStatusWpaPairwiseCipherSuite OBJECT-TYPE
   SYNTAX DisplayString
   MAX-ACCESS read-only
   STATUS current
   DESCRIPTION
   "Cipher suite being used for the WPA pairwise key."
   ::= { zbrWLanStatus 10 }

zbrWLanStatusAvailable OBJECT-TYPE
   SYNTAX DisplayString (SIZE (0..32))
   MAX-ACCESS read-only
   STATUS current
   DESCRIPTION
   "Wlan available."
   ::= { zbrWLanStatus 11 }

zbrWLanStatusSecuredViewEssid OBJECT-TYPE
   SYNTAX DisplayString (SIZE (0..32))
   MAX-ACCESS read-only
   STATUS current
   DESCRIPTION
   "Wlan secured_view_essid."
   ::= { zbrWLanStatus 12 }

zbrWLanRegulatoryDataVersion OBJECT-TYPE
   SYNTAX DisplayString (SIZE (0..32))
   MAX-ACCESS read-only
   STATUS current
   DESCRIPTION
   "Wlan regulatory data version."
   ::= { zbrWLanStatus 13 }


--=================================================================================================
-- zebra.zbrInterfaces.zbrIfWirelessLan.zbrWLanSettings
--=================================================================================================

zbrWLanSetupEnable OBJECT-TYPE
   SYNTAX INTEGER {
        on(1),
        off(2)
    }
   MAX-ACCESS read-write
   STATUS current
   DESCRIPTION
   "Enable the radio."
   ::= { zbrWLanSettings 1 }

zbrWLanSetupEssid OBJECT-TYPE
   SYNTAX DisplayString (SIZE (0..32))
   MAX-ACCESS read-write
   STATUS current
   DESCRIPTION
   "ESSID to be used for wireless connection."
   ::= { zbrWLanSettings 2 }

zbrWLanSetupOperatingMode OBJECT-TYPE
   SYNTAX INTEGER {
       ad-hoc(1),
       infrastructure(2)
   }
   MAX-ACCESS read-write
   STATUS current
   DESCRIPTION
   "Type of network for the radio to connect to."
   ::= { zbrWLanSettings 3 }

zbrWLanSetupAllowedBand OBJECT-TYPE
   SYNTAX INTEGER {
        all(1),
        band2-4GHz(2),
        band5GHz(3)
    }
   MAX-ACCESS read-write
   STATUS current
   DESCRIPTION
   "Which bands can the radio connect on."
   ::= { zbrWLanSettings 4 }

zbrWLanSetupInfrastructure2Point4GhzChannelMask OBJECT-TYPE
   SYNTAX INTEGER
   MAX-ACCESS read-write
   STATUS current
   DESCRIPTION
   "Bit mask describing what channels are acceptable for infrastructure connections in the 2.4GHz band.
   These are listed in pairs in the form: channel number(bit number).
   1(0), 2(1), 3(2), 4(3), 5(4), 6(5), 7(6), 8(7), 9(8), 10(9), 11(10), 12(11), 13(12), 14(13)"
   ::= { zbrWLanSettings 5 }

zbrWLanSetupInfrastructure5GhzChannelMask OBJECT-TYPE
   SYNTAX INTEGER
   MAX-ACCESS read-write
   STATUS current
   DESCRIPTION
   "Bit mask describing what channels are acceptable for infrastructure connections in the 5GHz band.
   These are listed in pairs in the form: channel number(bit number).
   34(0), 36(1), 38(2), 40(3), 42(4), 44(5), 46(6), 48(7), 52(8), 56(9),
   60(10), 64(11), 100(12),104(13),108(14),112(15),116(16),120(17),124(18),128(19),
   132(20),136(21),140(22),149(23),153(24),157(25),161(26),165(27)"
   ::= { zbrWLanSettings 6 }

zbrWLanSetupAdhocChannel OBJECT-TYPE
    SYNTAX INTEGER {
       wifi-channel-1(1),
       wifi-channel-2(2),
       wifi-channel-3(3),
       wifi-channel-4(4),
       wifi-channel-5(5),
       wifi-channel-6(6),
       wifi-channel-7(7),
       wifi-channel-8(8),
       wifi-channel-9(9),
       wifi-channel-10(10),
       wifi-channel-11(11),
       wifi-channel-12(12),
       wifi-channel-13(13),
       wifi-channel-14(14),
       wifi-channel-34(15),
       wifi-channel-36(16),
       wifi-channel-38(17),
       wifi-channel-40(18),
       wifi-channel-42(19),
       wifi-channel-44(20),
       wifi-channel-46(21),
       wifi-channel-48(22),
       wifi-channel-149(23),
       wifi-channel-153(24),
       wifi-channel-157(25),
       wifi-channel-161(26),
       wifi-channel-165(27)
    }
    MAX-ACCESS read-write
    STATUS current
    DESCRIPTION
    "Connection channel for an adhoc network."
    ::= { zbrWLanSettings 7 }

zbrWLanSetupInternationalModeEnable OBJECT-TYPE
   SYNTAX INTEGER {
        on(1),
        off(2)
    }
   MAX-ACCESS read-write
   STATUS current
   DESCRIPTION
   "Enable international mode."
   ::= { zbrWLanSettings 8 }

zbrWLanSetupPreambleLength OBJECT-TYPE
    SYNTAX INTEGER {
       long(1),
       short(2)
    }
    MAX-ACCESS read-write
    STATUS current
    DESCRIPTION
    "Length of preamble to use."
    ::= { zbrWLanSettings 9 }

zbrWLanSetupPowerSaveEnable OBJECT-TYPE
   SYNTAX INTEGER {
        on(1),
        off(2)
    }
   MAX-ACCESS read-write
   STATUS current
   DESCRIPTION
   "Enable power save mode."
   ::= { zbrWLanSettings 10 }

zbrWLanSetupRegionCode OBJECT-TYPE
   SYNTAX DisplayString (SIZE (0..32))
   MAX-ACCESS read-only
   STATUS current
   DESCRIPTION
   "Region code to define regulatory domain."
   ::= { zbrWLanSettings 12 }

zbrWLanSetupCountryCode OBJECT-TYPE
   SYNTAX DisplayString (SIZE (0..32))
   MAX-ACCESS read-write
   STATUS current
   DESCRIPTION
   "Country code within a regulatory domain."
   ::= { zbrWLanSettings 13 }

zbrWLanSetupPoorSignalThreshold OBJECT-TYPE
   SYNTAX INTEGER (0..100)
   MAX-ACCESS read-write
   STATUS current
   DESCRIPTION
   "The signal strength value which, at or below will cause a poor signal warning."
   ::= { zbrWLanSettings 14 }

zbrWLanProtectedManagementFrames OBJECT-TYPE
    SYNTAX INTEGER {
       disabled(1),
       enabled(2),
       required(3)
    }
    MAX-ACCESS read-write
    STATUS current
    DESCRIPTION
    "Disable, allow or require use of protected management frames."
    ::= { zbrWLanSettings 15 }
      
zbrWLanRtsCtsEnabled OBJECT-TYPE
   SYNTAX INTEGER {
        on(1),
        off(2)
    }
   MAX-ACCESS read-write
   STATUS current
   DESCRIPTION
   "Enable/disable 802.11n/ac RTS/CTS mode."
    ::= { zbrWLanSettings 16 }
      
zbrWLanSetupBandPreference OBJECT-TYPE
   SYNTAX INTEGER {
        none(1),
        band2-4GHz(2),
        band5GHz(3)
    }
   MAX-ACCESS read-write
   STATUS current
   DESCRIPTION
   "Which band has preference for the radio connect on."
   ::= { zbrWLanSettings 17 }
      
zbrWLanSetupDhcpRequired OBJECT-TYPE
   SYNTAX INTEGER {
        on(1),
        off(2)
    }
   MAX-ACCESS read-write
   STATUS current
   DESCRIPTION
   "DHCP request must be sent in order to access the network."
   ::= { zbrWLanSettings 18 }
   
--=================================================================================================
--zebra.zbrInterfaces.zbrIfWirelessLan.zbrWLanSettings.zbrWLanRoaming
--=================================================================================================

zbrWLanRoamSignal OBJECT-TYPE
   SYNTAX INTEGER (1..75)
   MAX-ACCESS read-write
   STATUS current
   DESCRIPTION
   "Trigger level of the signal strength to attempt to roam."
   ::= { zbrWLanRoaming 1 }

zbrWLanRoamInterval OBJECT-TYPE
   SYNTAX INTEGER (5..255)
   MAX-ACCESS read-write
   STATUS current
   DESCRIPTION
   "Interval between network scans."
   ::= { zbrWLanRoaming 2 }

zbrWLanRoamInterChannelDelay OBJECT-TYPE
   SYNTAX INTEGER (10..30000)
   MAX-ACCESS read-write
   STATUS current
   DESCRIPTION
   "Time between scans of each channel, in millisconds."
   ::= { zbrWLanRoaming 3 }

zbrWLanRoamMaxScanTime OBJECT-TYPE
   SYNTAX INTEGER (10..500)
   MAX-ACCESS read-write
   STATUS current
   DESCRIPTION
   "Time to scan each channel looking for connections, in milliseconds."
   ::= { zbrWLanRoaming 4 }

zbrWLanRoamRssi OBJECT-TYPE
   SYNTAX INTEGER (60..125)
   MAX-ACCESS read-write
   STATUS current
   DESCRIPTION
   "Trigger level of RSSI reading to attempt to roam."
   ::= { zbrWLanRoaming 5 }

zbrWLanRoamMaxFail OBJECT-TYPE
   SYNTAX INTEGER (2..75)
   MAX-ACCESS read-write
   STATUS current
   DESCRIPTION
   "Trigger count of failure attempts to attempt to roam."
   ::= { zbrWLanRoaming 6 }

zbrWLanRoamNeighborAssist OBJECT-TYPE
   SYNTAX INTEGER {
        on(1),
        off(2)
    }
   MAX-ACCESS read-write
   STATUS current
   DESCRIPTION
   "Enable/disable neighbor assist for 802.11k."
    ::= { zbrWLanRoaming 7 }

--=================================================================================================
--zebra.zbrInterfaces.zbrIfWirelessLan.zbrWLanSettings.zbrWLanKeepAlive
--=================================================================================================

zbrWLanKAEnable OBJECT-TYPE
   SYNTAX INTEGER {
        on(1),
        off(2)
    }
   MAX-ACCESS read-write
   STATUS current
   DESCRIPTION
   "Enable keep alive packets."
   ::= { zbrWLanKeepAlive 1 }

zbrWLanKAInterval OBJECT-TYPE
   SYNTAX INTEGER (5..300)
   MAX-ACCESS read-write
   STATUS current
   DESCRIPTION
   "Interval for keep alive packets to be sent, in seconds."
   ::= { zbrWLanKeepAlive 2 }

--=================================================================================================
--zebra.zbrInterfaces.zbrIfWirelessLan.zbrWLanSettings.zbrWLanElevenN
--=================================================================================================

zbrWLanElevenNGreenfieldEnable OBJECT-TYPE
   SYNTAX INTEGER {
        on(1),
        off(2)
    }
   MAX-ACCESS read-write
   STATUS current
   DESCRIPTION
   "Enable 802.11n Greenfield mode."
   ::= { zbrWLanElevenN 1 }

zbrWLanElevenNShortGuardInterval40MHzEnable OBJECT-TYPE
   SYNTAX INTEGER {
        on(1),
        off(2)
    }
   MAX-ACCESS read-write
   STATUS current
   DESCRIPTION
   "Enable use of the short guard interval on 40MHz bands."
   ::= { zbrWLanElevenN 2 }

zbrWLanElevenNShortGuardInterval20MHzEnable OBJECT-TYPE
   SYNTAX INTEGER {
        on(1),
        off(2)
    }
   MAX-ACCESS read-write
   STATUS current
   DESCRIPTION
   "Enable use of the short guard interval on 20MHz bands."
   ::= { zbrWLanElevenN 3 }

zbrWLanElevenNReducedInterframeSpace OBJECT-TYPE
   SYNTAX INTEGER {
        on(1),
        off(2)
    }
   MAX-ACCESS read-write
   STATUS current
   DESCRIPTION
   "Enable usage of reduced interframe spacing."
   ::= { zbrWLanElevenN 4 }

zbrWLanElevenN20MhzOnly OBJECT-TYPE
   SYNTAX INTEGER {
        on(1),
        off(2)
    }
   MAX-ACCESS read-write
   STATUS current
   DESCRIPTION
   "Channel bandwidth control."
   ::= { zbrWLanElevenN 5 }

zbrWLanElevenNPacketAggregation OBJECT-TYPE
   SYNTAX INTEGER {
        on(1),
        off(2)
    }
   MAX-ACCESS read-write
   STATUS current
   DESCRIPTION
   "Enable packet mode."
   ::= { zbrWLanElevenN 6 }

--=================================================================================================
--zebra.zbrInterfaces.zbrIfWirelessLan.zbrWLanSettings.zbrWLanElevenAC
--=================================================================================================

zbrWLanElevenACShortGuardInterval80MHzEnable OBJECT-TYPE
   SYNTAX INTEGER {
        on(1),
        off(2)
    }
   MAX-ACCESS read-write
   STATUS current
   DESCRIPTION
   "Enable use of the short guard interval on 80MHz bands."
   ::= { zbrWLanElevenAC 1 }

zbrWLanElevenACLowDensityParityCheckEnable OBJECT-TYPE
   SYNTAX INTEGER {
        on(1),
        off(2)
    }
   MAX-ACCESS read-write
   STATUS current
   DESCRIPTION
   "Enable use of low density parity check codes on 80MHz bands."
   ::= { zbrWLanElevenAC 2 }

zbrWLanElevenACSpaceTimeBlockCodingEnable OBJECT-TYPE
   SYNTAX INTEGER {
        on(1),
        off(2)
    }
   MAX-ACCESS read-write
   STATUS current
   DESCRIPTION
   "Enable use of space time block coding on 80MHz bands."
   ::= { zbrWLanElevenAC 3 }

zbrWLanElevenAC80MHzEnable OBJECT-TYPE
   SYNTAX INTEGER {
        on(1),
        off(2)
    }
   MAX-ACCESS read-write
   STATUS current
   DESCRIPTION
   "Allow use of 80MHz bands."
   ::= { zbrWLanElevenAC 4 }
   
--=================================================================================================
--zebra.zbrInterfaces.zbrIfWirelessLan.zbrWLanSecurity
--
-- Removed from zbrWLanSecurType as part of WEP deprecation and removing kerberos support
--      wep-40-bit(2),
--      wep-128-bit(3),
--      kerberos(15),
--=================================================================================================

zbrWLanSecurType OBJECT-TYPE
   SYNTAX INTEGER {
      none(1),
      eap-tls(4),
      eap-ttls(5),
      eap-fast(6),
      peap(7),
      leap(8),
      wpa-psk(9),
      wpa-eap-tls(10),
      wpa-eap-ttls(11),
      wpa-eap-fast(12),
      wpa-peap(13),
      wpa-leap(14),
      wpa-sae(17)
   }
   MAX-ACCESS read-write
   STATUS current
   DESCRIPTION
   "Security type to be used for wireless connections.
   The value of this setting will determine which of the other security OIDs will also be used."
   ::= { zbrWLanSecurity 1 }

zbrWLanSecurAuthenticationType OBJECT-TYPE
   SYNTAX INTEGER {
      open(1),
      shared(2)
   }
   MAX-ACCESS read-write
   STATUS current
   DESCRIPTION
   "authentication type used for connections using WPA security."
   ::= { zbrWLanSecurity 2 }

zbrWLanSecurUserName OBJECT-TYPE
   SYNTAX DisplayString (SIZE (0..64))
   MAX-ACCESS read-write
   STATUS current
   DESCRIPTION
   "username for securities that use it."
   ::= { zbrWLanSecurity 3 }

zbrWLanSecurPassword OBJECT-TYPE
   SYNTAX DisplayString (SIZE (0..32))
   MAX-ACCESS read-write
   STATUS current
   DESCRIPTION
   "password for securities that use one.  A get returns '*' not the current value."
   ::= { zbrWLanSecurity 4 }

zbrWLanSecurPrivateKeyPassword OBJECT-TYPE
   SYNTAX DisplayString (SIZE (0..32))
   MAX-ACCESS read-write
   STATUS current
   DESCRIPTION
   "Private key password for securities that use one.  A get returns '*' not the current value."
   ::= { zbrWLanSecurity 5 }

zbrWLanSecurPresharedKey OBJECT-TYPE
   SYNTAX DisplayString (SIZE (0..64))
   MAX-ACCESS read-write
   STATUS current
   DESCRIPTION
   "Preshared key for securities that use one.  A get returns '*' not the current value."
   ::= { zbrWLanSecurity 6 }

-- zbrWLanSecurEncryptionKeyFormat OBJECT-TYPE
--   ::= { zbrWLanSecurity 7 }

-- zbrWLanSecurEncryptionKeyIndex OBJECT-TYPE
--    ::= { zbrWLanSecurity 8 }

-- zbrWLanSecurEncryptionKey1 OBJECT-TYPE
--   ::= { zbrWLanSecurity 9 }

-- zbrWLanSecurEncryptionKey2 OBJECT-TYPE
--    ::= { zbrWLanSecurity 10 }

-- zbrWLanSecurEncryptionKey3 OBJECT-TYPE
--   ::= { zbrWLanSecurity 11 }

-- zbrWLanSecurEncryptionKey4 OBJECT-TYPE
--    ::= { zbrWLanSecurity 12 }

zbrWLanSecurTimeCheck OBJECT-TYPE
   SYNTAX INTEGER {
      yes(1),
      no(2)
   }
   MAX-ACCESS read-write
   STATUS current
   DESCRIPTION
    "Perform timestamp validation of certificates during WPA TLS handshake."
   ::= { zbrWLanSecurity 13 }

zbrWLanTtlsTunnel OBJECT-TYPE
   SYNTAX INTEGER {
      pap(1),
      chap(2),
      mschap(3),
      mschapv2(4)
   }
   MAX-ACCESS read-write
   STATUS current
   DESCRIPTION
   "Tunnel protocol to use when using EAP-TTLS"
   ::= { zbrWLanSecurity 14 }

zbrWLanValidatePeapServerCertificate OBJECT-TYPE
   SYNTAX  INTEGER {
      on(1),
      off(2)
   }
   MAX-ACCESS read-write
   STATUS current
   DESCRIPTION
   "Control the check of the server certificate when using PEAP security"
   ::= { zbrWLanSecurity 15 }

zbrWLanPeapAnonymousIdentity OBJECT-TYPE
   SYNTAX DisplayString (SIZE (0..32))
   MAX-ACCESS read-write
   STATUS current
   DESCRIPTION
   "anonymous identity to be used with PEAP."
   ::= { zbrWLanSecurity 16 }

zbrWLanTtlsAnonymousIdentity OBJECT-TYPE
   SYNTAX DisplayString (SIZE (0..32))
   MAX-ACCESS read-write
   STATUS current
   DESCRIPTION
   "anonymous identity to be used with TTLS."
   ::= { zbrWLanSecurity 17 }

--=================================================================================================
--zebra.zbrInterfaces.zbrIfWirelessLan.zbrWLanWaveAgent
--=================================================================================================

zbrWLanWAEnable OBJECT-TYPE
   SYNTAX INTEGER {
        on(1),
        off(2)
    }
   MAX-ACCESS read-write
   STATUS current
   DESCRIPTION
   "Enable wave agent."
   ::= { zbrWLanWaveAgent 1 }

zbrWLanWAUdpPort OBJECT-TYPE
   SYNTAX INTEGER (1..64000)
   MAX-ACCESS read-write
   STATUS current
   DESCRIPTION
   "Port to be used for wave agent communications."
   ::= { zbrWLanWaveAgent 2 }

--=================================================================================================
--zebra.zbrInterfaces.zbrIfWirelessLan.zbrWLanCcx
--=================================================================================================

zbrWLanCcxNeighborSupport OBJECT-TYPE
   SYNTAX INTEGER {
      on(1),
      off(2)
   }
   MAX-ACCESS read-write
   STATUS current
   DESCRIPTION
   "
   Enables/disables neighbor list processing by the roam agent. The neighbor list is provided unsolicited to all clients
   as they associate, and includes the scan threshold, transition time, minimum RSSI value for the AP, and hysteresis.
   The AP also provides periodic updates to associated clients."
   ::= { zbrWLanCcx 1 }
   
zbrWLanCcxAssistedRoam OBJECT-TYPE
   SYNTAX INTEGER {
      on(1),
      off(2)
   }
   MAX-ACCESS read-write
   STATUS current
   DESCRIPTION
   "
   Enable/disable the assisted roaming feature. AP-assisted roaming is a mechanism whereby the access point can provide
   intelligent advice to clients when they roam between access points. In the context of the overall wireless network
   in the venue, this means that the centralised wireless controller will be able to bump you off a busy access point/radio
   and on to one that is less congested, ensuring smoother operation for users of the wireless network."
   ::= { zbrWLanCcx 2 }   

zbrWLanCcxDirectedRoam OBJECT-TYPE
   SYNTAX INTEGER {
      on(1),
      off(2)
   }
   MAX-ACCESS read-write
   STATUS current
   DESCRIPTION
   "
   Enable/disable the directed roam feature. Directed roaming allows the AP to suggest a list of APs that the client might want to roam to."
   ::= { zbrWLanCcx 3 }

zbrWLanCcxL2RoamingEnhancements OBJECT-TYPE
   SYNTAX INTEGER {
      on(1),
      off(2)
   }
   MAX-ACCESS read-write
   STATUS current
   DESCRIPTION
   "
   Enable/disable the level 2 roaming enhancements feature. The ability to classify clients and have the clients participate in the roaming process
   through information gathered from the infrastructure provides client devices to improve predictability, reliability, an overall network performance.
   In contrast if devices are not classified, categorized, or participative in the roaming decision, specific legacy devices and applications could
   disrupt overall network performance. Examples of enhanced roaming classifications are - 'fast-roam', 'slow roam', 'a/b/g only'. Based on the
   classification of the clients by the network administrator as the Cisco Compatible Extensions device associates to the infrastructure, the access
   point will allow, deny or broadcast other AP's in the area that can provide service for the associating client. If the AP has the ability to service
   the client, association will occur and the access point will provide a list of neighboring access points that also have the ability to service the
   Cisco Compatible Extensions device with the specific feature classifications."
   ::= { zbrWLanCcx 4 }
      
zbrWLanCcxManagementFrameProtection OBJECT-TYPE
   SYNTAX INTEGER {
      on(1),
      off(2)
   }
   MAX-ACCESS read-write
   STATUS current
   DESCRIPTION
   "
   Enable/disable the management frame protection feature. One of the challenges in 802.11 has been that management frames are sent in the clear with no
   encryption or message integrity checking, and are therefore vulnerable to spoofing attacks. The spoofing of WLAN management frames can be used to attack
   the WLAN network. To address this, Cisco created a digital signature mechanism to insert a message integrity check (MIC) to 802.11 management frames.
   This allows the legitimate members of a WLAN deployment to be identified and therefore allows the identification of rogue infrastructure, and spoofed
   frames, through their lack of valid MICs. The MIC that is used in management frame protection (MFP) is not a simple CRC hashing of the message, but also
   includes a digital signature component. The MIC component of MFP ensures that a frame has not been tampered with and the digital signature component
   ensures that the MIC could have only been produced by a valid member of the WLAN domain. The digital signature key used in MFP is shared among all
   controllers in a mobility group; different mobility groups have different keys. This allows the validation of all WLAN management frames processed by the
   WLCs in that mobility group."
   ::= { zbrWLanCcx 5 }
   
zbrWLanCcxLinkTest OBJECT-TYPE
   SYNTAX INTEGER {
      on(1),
      off(2)
   }
   MAX-ACCESS read-write
   STATUS current
   DESCRIPTION
   "
   Enable/disable the link test feature. With the CCX link test, the controller can also test the link quality in the access point-to-client direction.
   The controller issues link-test requests to the client, and the client records the RF parameters [received signal strength indicator (RSSI),
   signal-to-noise ratio (SNR), etc.] of the received request packet in the response packet. Both the link-test requestor and responder roles are implemented
   on the access point and controller. Therefore, not only can the access point or controller initiate a link test to a CCX v4 client, but a CCX v4 client can
   initiate a link test to the access point or controller. The controller shows these link-quality metrics for CCX link tests in both directions (out: access
   point to client; in: client to access point): Signal strength in the form of RSSI (minimum, maximum, and average), Signal quality in the form of SNR (minimum,
   maximum, and average), Total number of packets that are retried, Maximum retry count for a single packet, Number of lost packets, Data rate of a successfully
   transmitted packet. The controller shows this metric regardless of direction: Link test request/reply round-trip time (minimum, maximum, and average). The 4.0
   release of controller software supports CCX versions 1 through 4. CCX support is enabled automatically for every WLAN on the controller and cannot be disabled.
   The controller stores the CCX version of the client in its client database and uses it to limit the features for this client. If a client does not support CCX
   v4, the controller performs a ping link test on the client. If a client supports CCX v4, the controller performs a CCX link test on the client. If a client
   times out during a CCX link test, the controller switches to the ping link test automatically."
   ::= { zbrWLanCcx 6 }

zbrWLanCcxTrafficStreamMetrics OBJECT-TYPE
   SYNTAX INTEGER {
      on(1),
      off(2)
   }
   MAX-ACCESS read-write
   STATUS current
   DESCRIPTION
   "
   Enable/disable the traffic stream metrics feature. In a voice-over-wireless LAN (VoWLAN) deployment, four variables can affect audio quality: packet latency,
   packet jitter, packet loss, and roaming time. These variables are referred to as traffic stream metrics (TSM). An administrator can isolate poor voice quality
   issues by studying these variables. The metrics consist of a collection of uplink (client side) and downlink (access point side) statistics between an access
   point and a client device that supports CCX v4. If the client is not CCX v4 compliant, only downlink statistics are captured. The client and access point measure
   these metrics. The access point also collects the measurements every 5 seconds, prepares 90-second reports, and then sends the reports to the controller. The
   controller organizes the uplink measurements on a client basis and the downlink measurements on an access point basis and maintains an hour's worth of historical
   data. To store this data, the controller requires 32 MB of additional memory for uplink metrics and 4.8 MB for downlink metrics. TSM can be configured through
   either the GUI or the CLI on a per radio-band basis (for example, all 802.11a radios). The controller saves the configuration in flash memory so that it persists
   across reboots. After an access point receives the configuration from the controller, it enables TSM on the specified radio band."
   ::= { zbrWLanCcx 7 }

zbrWLanCcxRadioManagement OBJECT-TYPE
   SYNTAX INTEGER {
      on(1),
      off(2)
   }
   MAX-ACCESS read-write
   STATUS current
   DESCRIPTION
   "
   Enable/disable the radio management feature, You can configure two parameters that affect client location calculations: Radio measurement requests, Location calibration.
   These parameters are supported in Cisco Client Extensions (CCX) v2 and higher and are designed to enhance location accuracy and timeliness for participating CCX clients.
   For the location features to operate properly, the access points must be configured for normal, monitor, or hybrid-REAP mode. However, for hybrid-REAP mode, the access
   point must be connected to the controller."
   ::= { zbrWLanCcx 8 }

zbrWLanCcxPathLossMeasurement OBJECT-TYPE
   SYNTAX INTEGER {
      on(1),
      off(2)
   }
   MAX-ACCESS read-write
   STATUS current
   DESCRIPTION
   "
   Enable/disable the path loss measurement feature so that the client participates/does not participate in path loss measurement by the AP.
   This allows the AP to calculate radio interference/loss levels between the AP and client."
   ::= { zbrWLanCcx 9 }
   
--=================================================================================================
--zebra.zbrInterfaces.zbrIfWirelessLan.zbrWLanIpv6
--=================================================================================================
   
zbrWLanIpv6AddrType OBJECT-TYPE
   SYNTAX INTEGER {
     static(1),
     auto(2)
   }
   MAX-ACCESS read-write
   STATUS current
   DESCRIPTION
   "DHCP request must be sent in order to access the network."
   ::= { zbrWLanIpv6 1 }   
   
zbrWLanIpv6Addresses OBJECT-TYPE
   SYNTAX DisplayString (SIZE (0..509))
   MAX-ACCESS read-only
   STATUS current
   DESCRIPTION
   "' shall be returned when no addresses are available."
   ::= { zbrWLanIpv6 2 }
   
zbrWLanIpv6Gateways OBJECT-TYPE
   SYNTAX DisplayString (SIZE (0..509))
   MAX-ACCESS read-only
   STATUS current
   DESCRIPTION
   "List of known gateways in use by the printer. Max list of 10."
   ::= { zbrWLanIpv6 3 }
   

--=================================================================================================
--zebra.zbrInterfaces.zbrIfWirelessLan.zbrWLanIpv6.zbrWLanIpv6Dhcp
--=================================================================================================

zbrWLanIpv6DhcpLeaseLength OBJECT-TYPE
   SYNTAX Unsigned32
   MAX-ACCESS read-only
   STATUS current
   DESCRIPTION
   "IPv6 DHCP lease time in seconds of preferred life."
   ::= { zbrWLanIpv6Dhcp 1 }

zbrWLanIpv6DhcpLeaseTimeLeft OBJECT-TYPE
   SYNTAX Unsigned32
   MAX-ACCESS read-only
   STATUS current
   DESCRIPTION
   "IPv6 DHCP lease time left in seconds of preferred life."
   ::= { zbrWLanIpv6Dhcp 2 }

zbrWLanIpv6DhcpLeaseLastAttempt OBJECT-TYPE
   SYNTAX Unsigned32
   MAX-ACCESS read-only
   STATUS current
   DESCRIPTION
   "IPv6 DHCP lease last attemp time in UNIX timestamp."
   ::= { zbrWLanIpv6Dhcp 3 }

zbrWLanIpv6DhcpOption39Enable OBJECT-TYPE
   SYNTAX INTEGER {
      on(1),
      off(2)
   }
   MAX-ACCESS read-write
   STATUS current
   DESCRIPTION
   "
   Control the inclusion of option39 in DHCPv6 communication."
   ::= { zbrWLanIpv6Dhcp 4 }

zbrWLanIpv6DhcpOption39Format OBJECT-TYPE
   SYNTAX DisplayString (SIZE (0..127))
   MAX-ACCESS read-write
   STATUS current
   DESCRIPTION
   "
   The format string that determines the value for option39 used in DHCPv6 packets."
   ::= { zbrWLanIpv6Dhcp 5 }

zbrWLanIpv6DhcpOption39Value OBJECT-TYPE
   SYNTAX DisplayString (SIZE (0..127))
   MAX-ACCESS read-only
   STATUS current
   DESCRIPTION
   "
   The processed value derived from option39_format field. Will be used as the DHCPv6 option39 value."
   ::= { zbrWLanIpv6Dhcp 6 }

zbrWLanIpv6DhcpOption39Fqdn OBJECT-TYPE
   SYNTAX DisplayString (SIZE (0..127))
   MAX-ACCESS read-only
   STATUS current
   DESCRIPTION
   "
   The fully qualified domain name of the printer as given by the DHCPv6 server."
   ::= { zbrWLanIpv6Dhcp 7 }

--===========================
--zebra.zbrInterfaces.zbrIfWirelessLan.zbrWLanIpv6.zbrWLanIpv6Static
--===========================
   
zbrWLanIpv6StaticAddresses OBJECT-TYPE
   SYNTAX DisplayString (SIZE (0..152))
   MAX-ACCESS read-write
   STATUS current
   DESCRIPTION
   "' when no static address has been set."
   ::= { zbrWLanIpv6Static 1 }
   
zbrWLanIpv6StaticGateways OBJECT-TYPE
   SYNTAX DisplayString (SIZE (0..50))
   MAX-ACCESS read-write
   STATUS current
   DESCRIPTION
   "' when no static address has been set."
   ::= { zbrWLanIpv6Static 2 }
      

--=================================================================================================
--zebra.zbrInterfaces.zbrNetwork
--=================================================================================================

zbrNetPrimaryNetworkType OBJECT-TYPE
   SYNTAX INTEGER {
      wired(1),
      wireless(2)
   }
   MAX-ACCESS read-write
   STATUS current
   DESCRIPTION
    "The type of network the system should first attempt to use on a network reset."
   ::= { zbrNetwork 1 }

zbrNetActiveNetworkInterface OBJECT-TYPE
   SYNTAX INTEGER {
      external-wired(1),
      internal-wired(2),
      wireless(3),
      unknown(4)
   }
   MAX-ACCESS read-only
   STATUS current
   DESCRIPTION
    "The network interface the system is currently using for network connectivity."
   ::= { zbrNetwork 2 }

zbrNetSettingsDirty OBJECT-TYPE
   SYNTAX INTEGER {
      no(1),
      yes(2)
   }
   MAX-ACCESS read-only
   STATUS current
   DESCRIPTION
    "This flag will be set if a network setting has been changed and needs a network
       reset in order to take effect."
   ::= { zbrNetwork 3 }

zbrNetInternalWiredSettingLocation OBJECT-TYPE
   SYNTAX INTEGER {
      printserver(1),
      printer(2)
   }
   MAX-ACCESS read-write
   STATUS current
   DESCRIPTION
   "The location from where internal_wired network specific settings should be retrieved."
   ::= { zbrNetwork 6 }


--=================================================================================================
--zebra.zbrInterfaces.zbrNetwork.zbrNetCommands
--=================================================================================================

zbrNCmdPrintNetworkConfigLabel OBJECT-TYPE
   SYNTAX INTEGER {
        no(1),
        yes(2)
    }
    MAX-ACCESS  read-write
    STATUS  current
    DESCRIPTION
    "Prints a network configuration label."
    ::={ zbrNetCommands 1 }

zbrNCmdResetNetwork  OBJECT-TYPE
   SYNTAX INTEGER {
        no(1),
        yes(2)
    }
    MAX-ACCESS  read-write
    STATUS  current
    DESCRIPTION
    "Resets the network stack. Your printer will lose connectivity for up to 2 minutes."
    ::={ zbrNetCommands 2 }

zbrNCmdDefaultAllNetworkSettings  OBJECT-TYPE
   SYNTAX INTEGER {
        no(1),
        yes(2)
    }
    MAX-ACCESS  read-write
    STATUS  current
    DESCRIPTION
    "Defaults all network settings, including interface specific settings.  Setting
        this OID will perform a network reset."
    ::={ zbrNetCommands 3 }

--=================================================================================================
--zebra.zbrInterfaces.zbrNetwork.zbrNetCommonNetworkSettings
--=================================================================================================
zbrNetIpPingGatewayInterval OBJECT-TYPE
   SYNTAX INTEGER (0..30)
   MAX-ACCESS read-write
   STATUS current
   DESCRIPTION
   "The IP getway ping interval in minutes.  An ICMP PING request will be sent to the IP gateway at this interval.
      Set to 0 to disable."
   ::= { zbrNetCommonNetworkSettings 1 }
   
zbrNetIpAddressMode OBJECT-TYPE
   SYNTAX INTEGER {
      ipv4(1),
      ipv6(2),
      all(3)
   }
   MAX-ACCESS read-write
   STATUS current
   DESCRIPTION
   "The IP protocol for network operation."
   ::={ zbrNetCommonNetworkSettings 2 }   

--=================================================================================================
--zebra.zbrInterfaces.zbrNetwork.zbrNetCommonNetworkSettings.zbrNetProtocols
--=================================================================================================

--=================================================================================================
--zebra.zbrInterfaces.zbrNetwork.zbrNetCommonNetworkSettings.zbrNetProtocols.zbrNetProtoTcp
--=================================================================================================
zbrTcpRawEnable OBJECT-TYPE
  SYNTAX INTEGER {
      no(1),
      yes(2)
   }
   MAX-ACCESS read-write
   STATUS current
   DESCRIPTION
    "Enable or disable RAW tcp/ip connections to the printer. Requires a network reset
      to take effect."
   ::= { zbrNetProtoTcp 1 }

-- moved to ZEBRA-MIB-OBSOLETE as they were never implimented.  Firewall used instead of SecurityTable
-- zbrTcpNumSecurity OBJECT-TYPE
--   ::= { zbrNetProtoTcp 10 }
-- zbrTcpSecurityTable OBJECT-TYPE
--    ::= { zbrNetProtoTcp 11 }
-- zbrTcpNumLogicalPrinters OBJECT-TYPE
--   ::= { zbrNetProtoTcp 12 }
-- zbrTcpMLPTable OBJECT-TYPE
--      ::= { zbrNetProtoTcp 13 }


zbrTcpPortSingleConn OBJECT-TYPE
   SYNTAX INTEGER (0..65535)
   MAX-ACCESS read-write
   STATUS current
   DESCRIPTION
   "A TCP port number on which to listen for the TCP Single Connection interface.
   The default port is 9300.  Setting this value to a TCP port that is in use by
   another TCP application will return an error."
   ::= { zbrNetProtoTcp 14 }
   
zbrTcpPortSingleConnIdleTimeout OBJECT-TYPE
   SYNTAX INTEGER (0..3600)
   MAX-ACCESS read-write
   STATUS current
   DESCRIPTION
   "Time in seconds of inactivity at which point the Single Connection
   interface is considered idle. An idle connection will be replaced (and closed) when a new connection occurs.
   A value of 0 means the connection is always considered idle and can be replaced by a new connection at any time."
   ::= { zbrNetProtoTcp 15 }

zbrTcpNagleAlgorithmEnable OBJECT-TYPE
  SYNTAX INTEGER {
      no(1),
      yes(2)
   }
   MAX-ACCESS read-write
   STATUS current
   DESCRIPTION
    "Enable or disable Nagle Algorithm on TCP connections to the printer. Requires a network reset
      to take effect."
   ::= { zbrNetProtoTcp 16 }
      
--=================================================================================================
--zebra.zbrInterfaces.zbrNetwork.zbrNetCommonNetworkSettings.zbrNetProtocols.zbrNetProtoFtp
--=================================================================================================

zbrNetFtpEnable OBJECT-TYPE
   SYNTAX INTEGER {
      no(1),
      yes(2)
   }
   MAX-ACCESS read-write
   STATUS current
   DESCRIPTION
    "Enable or disable FTP.  Changing this setting requires a network reset."
   ::= { zbrNetProtoFtp 1 }

zbrNetFtpPasswordRequestEnable OBJECT-TYPE
   SYNTAX INTEGER {
      no(1),
      yes(2)
   }
   MAX-ACCESS read-write
   STATUS current
   DESCRIPTION
    "Enable the FTP server to request a password upon client connection."
   ::= { zbrNetProtoFtp 2 }

--=================================================================================================
--zebra.zbrInterfaces.zbrNetwork.zbrNetCommonNetworkSettings.zbrNetProtocols.zbrNetProtoLpd
--=================================================================================================

zbrLpdEnable OBJECT-TYPE
   SYNTAX INTEGER {
      no(1),
      yes(2)
   }
   MAX-ACCESS read-write
   STATUS current
   DESCRIPTION
    "Enable or disable LPD.  Changing this setting requires a network reset."
   ::= { zbrNetProtoLpd 1 }

--=================================================================================================
--zebra.zbrInterfaces.zbrNetwork.zbrNetCommonNetworkSettings.zbrNetProtocols.zbrNetProtoMail
--=================================================================================================

zbrMailDomainName OBJECT-TYPE
   SYNTAX DisplayString (SIZE (0..25))
   MAX-ACCESS read-write
   STATUS current
   DESCRIPTION
    "Domain name used for both POP3 and SMTP mail services."
   ::= { zbrNetProtoMail 1 }

--=================================================================================================
--zebra.zbrInterfaces.zbrNetwork.zbrNetCommonNetworkSettings.zbrNetProtocols.zbrNetProtoMail.zbrNetProtoSmtp
--=================================================================================================

zbrSmtpEnable OBJECT-TYPE
   SYNTAX INTEGER {
      no(1),
      yes(2)
   }
   MAX-ACCESS read-write
   STATUS current
   DESCRIPTION
    "Enable or disable SMTP.  Changing this setting requires a network reset."
   ::= { zbrNetProtoSmtp 1 }

zbrSmtpServerAddress OBJECT-TYPE
   SYNTAX DisplayString (SIZE (0..41))
   MAX-ACCESS read-write
   STATUS current
   DESCRIPTION
    "IP Address of SMTP server."
   ::= { zbrNetProtoSmtp 2 }

--=================================================================================================
--zebra.zbrInterfaces.zbrNetwork.zbrNetCommonNetworkSettings.zbrNetProtocols.zbrNetProtoMail.zbrNetProtoPop3
--=================================================================================================

zbrPop3Enable OBJECT-TYPE
   SYNTAX INTEGER {
      no(1),
      yes(2)
   }
   MAX-ACCESS read-write
   STATUS current
   DESCRIPTION
    "Enable or disable POP3.  Changing this setting requires a network reset."
   ::= { zbrNetProtoPop3 1 }

zbrPop3ServerAddress OBJECT-TYPE
   SYNTAX DisplayString (SIZE (0..41))
   MAX-ACCESS read-write
   STATUS current
   DESCRIPTION
    "IP Address of POP3 server."
   ::= { zbrNetProtoPop3 2 }

zbrPop3username OBJECT-TYPE
   SYNTAX DisplayString (SIZE (0..64))
   MAX-ACCESS read-write
   STATUS current
   DESCRIPTION
    "POP3 username."
   ::= { zbrNetProtoPop3 3 }

zbrPop3password OBJECT-TYPE
   SYNTAX DisplayString (SIZE (0..21))
   MAX-ACCESS read-write
   STATUS current
   DESCRIPTION
    "POP3 password."
   ::= { zbrNetProtoPop3 4 }

zbrPop3PollingInterval OBJECT-TYPE
   SYNTAX INTEGER
   MAX-ACCESS read-write
   STATUS current
   DESCRIPTION
    "POP3 Polling interval."
   ::= { zbrNetProtoPop3 5 }

--=================================================================================================
--zebra.zbrInterfaces.zbrNetwork.zbrNetCommonNetworkSettings.zbrNetProtocols.zbrNetProtoTelnet
--=================================================================================================


--=================================================================================================
--zebra.zbrInterfaces.zbrNetwork.zbrNetCommonNetworkSettings.zbrNetProtocols.zbrNetProtoUdp
--=================================================================================================
zbrUdpRawEnable OBJECT-TYPE
   SYNTAX INTEGER {
      no(1),
      yes(2)
   }
   MAX-ACCESS read-write
   STATUS current
   DESCRIPTION
    "Enable or disable RAW UDP connections.  Changing this setting requires a network reset."
   ::= { zbrNetProtoUdp 1 }

zbrUdpDiscoveryPort OBJECT-TYPE
   SYNTAX INTEGER
   MAX-ACCESS read-write
   STATUS current
   DESCRIPTION
    "The port that will respond to UDP discovery requests.  The default is 4201."
   ::= { zbrNetProtoUdp 2 }

--=================================================================================================
--zebra.zbrInterfaces.zbrNetwork.zbrNetCommonNetworkSettings.zbrNetProtocols.zbrNetProtoHttp
--=================================================================================================

zbrHttpEnable OBJECT-TYPE
   SYNTAX INTEGER {
      no(1),
      yes(2)
   }
   MAX-ACCESS read-write
   STATUS current
   DESCRIPTION
    "Enable or disable HTTP.  Changing this setting requires a network reset."
   ::= { zbrNetProtoHttp 1 }

zbrHttpPort OBJECT-TYPE
   SYNTAX INTEGER
   MAX-ACCESS read-write
   STATUS current
   DESCRIPTION
    "HTTP Port for use with web pages.  Default is 80."
   ::= { zbrNetProtoHttp 2 }

zbrHttpWebAdminName OBJECT-TYPE
   SYNTAX DisplayString (SIZE (0..25))
   MAX-ACCESS read-write
   STATUS current
   DESCRIPTION
    "HTTP Web Admin name for use with the print server web pages."
   ::= { zbrNetProtoHttp 3 }

zbrHttpWebAdminPassword OBJECT-TYPE
   SYNTAX DisplayString (SIZE (0..25))
   MAX-ACCESS read-write
   STATUS current
   DESCRIPTION
    "HTTP Web Admin password for use with the print server web pages."
   ::= { zbrNetProtoHttp 4 }

zbrHttpWebFaqUrl OBJECT-TYPE
   SYNTAX DisplayString (SIZE (0..64))
   MAX-ACCESS read-write
   STATUS current
   DESCRIPTION
    "Web FAQ URL."
   ::= { zbrNetProtoHttp 5 }

zbrHttpWebUpdateUrl OBJECT-TYPE
   SYNTAX DisplayString (SIZE (0..64))
   MAX-ACCESS read-write
   STATUS current
   DESCRIPTION
    "Web Update URL."
   ::= { zbrNetProtoHttp 6 }

zbrHttpWebCustomLinkName OBJECT-TYPE
   SYNTAX DisplayString (SIZE (0..25))
   MAX-ACCESS read-write
   STATUS current
   DESCRIPTION
    "Web Custom Link Name."
   ::= { zbrNetProtoHttp 7 }

zbrHttpWebCustomLinkUrl OBJECT-TYPE
   SYNTAX DisplayString (SIZE (0..64))
   MAX-ACCESS read-write
   STATUS current
   DESCRIPTION
    "Web Custom Link URL."
   ::= { zbrNetProtoHttp 8 }

--=================================================================================================
--zebra.zbrInterfaces.zbrNetwork.zbrNetCommonNetworkSettings.zbrNetProtocols.zbrNetProtoSnmp
--=================================================================================================

zbrNetSnmpEnable OBJECT-TYPE
   SYNTAX INTEGER {
      no(1),
      yes(2)
   }
   MAX-ACCESS read-write
   STATUS current
   DESCRIPTION
    "Enable or disable SNMP.  Changing this setting requires a network reset."
   ::= { zbrNetProtoSnmp 1 }

zbrNetSnmpGetCommunityName OBJECT-TYPE
   SYNTAX DisplayString (SIZE (0..31))
   MAX-ACCESS read-write
   STATUS current
   DESCRIPTION
    "The snmp get community name."
   ::= { zbrNetProtoSnmp 2 }

zbrNetSnmpSetCommunityName OBJECT-TYPE
   SYNTAX DisplayString (SIZE (0..31))
   MAX-ACCESS read-write
   STATUS current
   DESCRIPTION
    "The snmp set community name. Was write-only"
   ::= { zbrNetProtoSnmp 3 }

zbrNetSnmpTrapCommunityName OBJECT-TYPE
   SYNTAX DisplayString (SIZE (0..31))
   MAX-ACCESS read-write
   STATUS current
   DESCRIPTION
    "The snmp trap community name."
   ::= { zbrNetProtoSnmp 4 }

zbrNetSnmpRestoreDefaults OBJECT-TYPE
   SYNTAX INTEGER {
      no(1),
      yes(2)
   }
   MAX-ACCESS read-write
   STATUS current
   DESCRIPTION
    "Restore defaults to SNMP values."
   ::= { zbrNetProtoSnmp 5 }

--=================================================================================================
--zebra.zbrInterfaces.zbrNetwork.zbrNetCommonNetworkSettings.zbrNetProtocols.zbrNetProtoNtp
--=================================================================================================

zbrNetNtpEnable OBJECT-TYPE
   SYNTAX INTEGER {
      on(1),
      off(2)
   }
   MAX-ACCESS read-write
   STATUS current
   DESCRIPTION
    "Enable or disable NTP.  Changing this setting requires a network reset.  You should set zbrRtcTimezone when using this feature."
   ::= { zbrNetProtoNtp 1 }

zbrNetNtpServers OBJECT-TYPE
   SYNTAX OCTET STRING (SIZE (0..1024))
   MAX-ACCESS read-write
   STATUS current
   DESCRIPTION
    "Comma delimited list of NTP server name(s) or IP address(es)."
   ::= { zbrNetProtoNtp 2 }

--=================================================================================================
--zebra.zbrInterfaces.zbrNetwork.zbrNetCommonNetworkSettings.zbrNetProtocols.zbrNetProtoTls
--=================================================================================================

zbrNetTlsEnable OBJECT-TYPE
   SYNTAX INTEGER {
      on(1),
      off(2)
   }
   MAX-ACCESS read-write
   STATUS current
   DESCRIPTION
    "Enable or disable TLS.  Changing this setting requires a network reset."
   ::= { zbrNetProtoTls 1 }

zbrNetTlsPort OBJECT-TYPE
   SYNTAX INTEGER
   MAX-ACCESS read-write
   STATUS current
   DESCRIPTION
    "Port for use with encrypted raw port.  Default is 9143. Requires a network reset to take effect."
   ::= { zbrNetProtoTls 2 }

zbrNetTlsPortJsonConfig OBJECT-TYPE
   SYNTAX INTEGER
   MAX-ACCESS read-write
   STATUS current
   DESCRIPTION
    "Port for use with encrypted json configuration port.  Default is 9243. Requires a network reset to take effect."
   ::= { zbrNetProtoTls 3 }

zbrNetTlsCiphers OBJECT-TYPE
   SYNTAX OCTET STRING (SIZE (0..256))
   MAX-ACCESS read-write
   STATUS current
   DESCRIPTION
    "List of ciphers to support over the TLS connection. Requires a network reset to take effect."
   ::= { zbrNetProtoTls 4 }

--=================================================================================================
--zebra.zbrInterfaces.zbrNetwork.zbrNetCommonNetworkSettings.zbrNetProtocols.zbrNetProtoHttps
--=================================================================================================

zbrNetHttpsEnable OBJECT-TYPE
   SYNTAX INTEGER {
      on(1),
      off(2)
   }
   MAX-ACCESS read-write
   STATUS current
   DESCRIPTION
    "Enable or disable HTTPS.  Changing this setting requires a network reset."
   ::= { zbrNetProtoHttps 1 }

zbrNetHttpsPort OBJECT-TYPE
   SYNTAX INTEGER
   MAX-ACCESS read-write
   STATUS current
   DESCRIPTION
    "Port for use with HTTPS.  Default is 443. Requires a network reset to take effect."
   ::= { zbrNetProtoHttps 2 }

zbrNetHttpsCiphers OBJECT-TYPE
   SYNTAX OCTET STRING (SIZE (0..256))
   MAX-ACCESS read-write
   STATUS current
   DESCRIPTION
    "List of ciphers to support over the HTTPS connection. Requires a network reset to take effect."
   ::= { zbrNetProtoHttps 3 }

--=================================================================================================
--zebra.zbrInterfaces.zbrNetwork.zbrNetCommonNetworkSettings.zbrNetProtocols.zbrNetProtoMqtt
--=================================================================================================

zbrNetMqttEnable OBJECT-TYPE
   SYNTAX INTEGER {
      on(1),
      off(2)
   }
   MAX-ACCESS read-write
   STATUS current
   DESCRIPTION
    "Enable or disable MQTT.  Takes effect immediately, starting/stopping mqtt connections."
   ::= { zbrNetProtoMqtt 1 }

zbrNetMqttRestoreDefaults OBJECT-TYPE
   SYNTAX  INTEGER {
       no(1),
       yes(2)    }
    MAX-ACCESS read-write
   STATUS current
   DESCRIPTION
   "Defaults the mqtt branch settings"
   ::= { zbrNetProtoMqtt 2 }
   
--=================================================================================================
--zebra.zbrInterfaces.zbrNetwork.zbrNetCommonNetworkSettings.zbrNetProtocols.zbrNetProtoMqtt.zbrNetProtoMqttConn1
--=================================================================================================
zbrNetProtoMqttConn1ServerAddress OBJECT-TYPE
   SYNTAX  OCTET STRING (SIZE (0..2048))
   MAX-ACCESS read-write
   STATUS current
   DESCRIPTION
   " Assigns the URL of the server for this connection. 
      The URL must follow common URL <scheme>://<domain>[:port][/Path].  
      When this setting's value changeszbrNetProtoMqttConn1ResetRequired will be set to yes to indicate 
      that the connection must be reset for this setting to take effect"
   ::= { zbrNetProtoMqttConn1 1 }

zbrNetProtoMqttConn1Version OBJECT-TYPE
   SYNTAX INTEGER {
      version-3-1-1(1)
   }
   MAX-ACCESS read-write
   STATUS current
   DESCRIPTION
    "Specifies the MQTT version of the broker."
   ::= { zbrNetProtoMqttConn1 2 }
    
zbrNetProtoMqttConn1UserName OBJECT-TYPE
   SYNTAX  DisplayString (SIZE (0..64))
   MAX-ACCESS read-write
   STATUS  current
   DESCRIPTION
   "Specifies the username to use for this connection"
   ::= { zbrNetProtoMqttConn1 3 }
    
zbrNetProtoMqttConn1Password OBJECT-TYPE
   SYNTAX  DisplayString (SIZE (0..64))
   MAX-ACCESS read-write
   STATUS  current
   DESCRIPTION
   "Specifies the password for the MQTT connection."
   ::= { zbrNetProtoMqttConn1 4 }
    
zbrNetProtoMqttConn1Qos OBJECT-TYPE
   SYNTAX INTEGER (1..2)
   MAX-ACCESS read-write
   STATUS  current
   DESCRIPTION
   "Specifies the quality of service to support for this connection"
   ::= { zbrNetProtoMqttConn1 5 }
    
zbrNetProtoMqttConn1RetryIntervalRandomMax OBJECT-TYPE
   SYNTAX INTEGER (1..600)
   MAX-ACCESS read-write
   STATUS  current
   DESCRIPTION
   " The maximum number of seconds between attempts to connect to the
    server URL provided in zbrNetProtoMqttConn1ServerAddress. If an attempt is unsuccessful or the connection is lost, 
    the printer will wait a random number of seconds between 1 and this value to attempting to connect again."  
   ::= { zbrNetProtoMqttConn1 6 }
    
zbrNetProtoMqttConn1CleanSessionFlag OBJECT-TYPE
   SYNTAX INTEGER {
      on(1),
      off(2)
   }
   MAX-ACCESS read-write
   STATUS current
   DESCRIPTION
    "If 'on', clear queued messages (clean session) when establishing this MQTT connection."
   ::= { zbrNetProtoMqttConn1 7 }
   
zbrNetProtoMqttConn1PingInterval OBJECT-TYPE
   SYNTAX INTEGER (1..300)
   MAX-ACCESS read-write
   STATUS  current
   DESCRIPTION
   " Specifies the interval in seconds at which to send mqtt pings to keep this connection open."  
   ::= { zbrNetProtoMqttConn1 8 }   
   
zbrNetProtoMqttConn1ResetNow OBJECT-TYPE
   SYNTAX  INTEGER {
       no(1),
       yes(2)    }
   MAX-ACCESS read-write
   STATUS current
   DESCRIPTION
   "Reset this mqtt connection and apply any recently changed settings."
   ::= { zbrNetProtoMqttConn1 9 }
   
zbrNetProtoMqttConn1ResetRequired OBJECT-TYPE
   SYNTAX  INTEGER {
       no(1),
       yes(2)    }
   MAX-ACCESS read-only
   STATUS current
   DESCRIPTION
   "Shows if a reset is required for any recent mqtt setting changes to take effect."
   ::= { zbrNetProtoMqttConn1 10 }
   
zbrNetProtoMqttConn1TenantId OBJECT-TYPE
   SYNTAX  DisplayString (SIZE (1..64))
   MAX-ACCESS read-write
   STATUS  current
   DESCRIPTION
   "Specifies the top level topic the printer will subscribe/publish to for this connection"
   ::= { zbrNetProtoMqttConn1 11 }
   
--=================================================================================================
--zebra.zbrInterfaces.zbrNetwork.zbrNetCommonNetworkSettings.zbrNetProtocols.zbrNetProtoMqtt.zbrNetProtoMqttConn2
--=================================================================================================
zbrNetProtoMqttConn2ServerAddress OBJECT-TYPE
   SYNTAX  OCTET STRING (SIZE (0..2048))
   MAX-ACCESS read-write
   STATUS current
   DESCRIPTION
   " Assigns the URL of the server for this connection. 
      The URL must follow common URL <scheme>://<domain>[:port][/Path].  
      When this setting's value changeszbrNetProtoMqttConn1ResetRequired will be set to yes to indicate 
      that the connection must be reset for this setting to take effect"
   ::= { zbrNetProtoMqttConn2 1 }

zbrNetProtoMqttConn2Version OBJECT-TYPE
   SYNTAX INTEGER {
      version-3-1-1(1)
   }
   MAX-ACCESS read-write
   STATUS current
   DESCRIPTION
    "Specifies the MQTT version of the broker."
   ::= { zbrNetProtoMqttConn2 2 }
    
zbrNetProtoMqttConn2UserName OBJECT-TYPE
   SYNTAX  DisplayString (SIZE (0..64))
   MAX-ACCESS read-write
   STATUS  current
   DESCRIPTION
   "Specifies the username to use for this connection"
   ::= { zbrNetProtoMqttConn2 3 }
    
zbrNetProtoMqttConn2Password OBJECT-TYPE
   SYNTAX  DisplayString (SIZE (0..64))
   MAX-ACCESS read-write
   STATUS  current
   DESCRIPTION
   "Specifies the password for the MQTT connection."
   ::= { zbrNetProtoMqttConn2 4 }
    
zbrNetProtoMqttConn2Qos OBJECT-TYPE
   SYNTAX INTEGER (1..2)
   MAX-ACCESS read-write
   STATUS  current
   DESCRIPTION
   "Specifies the quality of service to support for this connection"
   ::= { zbrNetProtoMqttConn2 5 }
    
zbrNetProtoMqttConn2RetryIntervalRandomMax OBJECT-TYPE
   SYNTAX INTEGER (1..600)
   MAX-ACCESS read-write
   STATUS  current
   DESCRIPTION
   " The maximum number of seconds between attempts to connect to the
    server URL provided in zbrNetProtoMqttConn2ServerAddress. If an attempt is unsuccessful or the connection is lost, 
    the printer will wait a random number of seconds between 1 and this value to attempting to connect again."  
   ::= { zbrNetProtoMqttConn2 6 }
    
zbrNetProtoMqttConn2CleanSessionFlag OBJECT-TYPE
   SYNTAX INTEGER {
      on(1),
      off(2)
   }
   MAX-ACCESS read-write
   STATUS current
   DESCRIPTION
    "If 'on', clear queued messages (clean session) when establishing this MQTT connection."
   ::= { zbrNetProtoMqttConn2 7 }
   
zbrNetProtoMqttConn2PingInterval OBJECT-TYPE
   SYNTAX INTEGER (1..300)
   MAX-ACCESS read-write
   STATUS  current
   DESCRIPTION
   " Specifies the interval in seconds at which to send mqtt pings to keep this connection open."  
   ::= { zbrNetProtoMqttConn2 8 }   
   
zbrNetProtoMqttConn2ResetNow OBJECT-TYPE
   SYNTAX  INTEGER {
       no(1),
       yes(2)    }
   MAX-ACCESS read-write
   STATUS current
   DESCRIPTION
   "Reset this mqtt connection and apply any recently changed settings."
   ::= { zbrNetProtoMqttConn2 9 }
   
zbrNetProtoMqttConn2ResetRequired OBJECT-TYPE
   SYNTAX  INTEGER {
       no(1),
       yes(2)    }
   MAX-ACCESS read-only
   STATUS current
   DESCRIPTION
   "Shows if a reset is required for any recent mqtt setting changes to take effect."
   ::= { zbrNetProtoMqttConn2 10 }
   
zbrNetProtoMqttConn2TenantId OBJECT-TYPE
   SYNTAX  DisplayString (SIZE (1..64))
   MAX-ACCESS read-write
   STATUS  current
   DESCRIPTION
   "Specifies the top level topic the printer will subscribe/publish to for this connection"
   ::= { zbrNetProtoMqttConn2 11 }
 
--=================================================================================================
--zebra.zbrNetProtoMqtt.zbrNetProtoMqttLogging
--=================================================================================================
zbrMqttLoggingMaxEntries OBJECT-TYPE
   SYNTAX INTEGER (0..10000)
   MAX-ACCESS read-write
   STATUS current
   DESCRIPTION
   "The maximum number of entries in the log. Setting this value to 0 disables logging."
   ::= { zbrNetProtoMqttLogging 1 }

zbrMqttLoggingClear OBJECT-TYPE
   SYNTAX  INTEGER {
       no(1),
       yes(2)    }
    MAX-ACCESS read-write
   STATUS current
   DESCRIPTION
   "Clears the MQTT log when set to yes(2)."
   ::= { zbrNetProtoMqttLogging 2 }

--=================================================================================================
--zebra.zbrInterfaces.zbrNetwork.zbrNetCommonNetworkSettings.zbrNetProtocols.zbrNetProtoSnmpv3
--=================================================================================================
   
zbrNetSnmpv3Enable OBJECT-TYPE
   SYNTAX INTEGER {
      no(1),
      yes(2)
   }
   MAX-ACCESS read-only
   STATUS current
   DESCRIPTION
   "Whether SNMPv3 is enabled or not."
   ::= { zbrNetProtoSnmpv3 1 }

--=================================================================================================
--zebra.zbrInterfaces.zbrNetwork.zbrNetCommonNetworkSettings.zbrNetProtocols.zbrNetProtoSnmpv3.zbrNetProtoSnmpv3Admin
--=================================================================================================

zbrNetSnmpv3AdminName OBJECT-TYPE
   SYNTAX DisplayString (SIZE (0..32))
   MAX-ACCESS read-only
   STATUS current
   DESCRIPTION
   "Admin user's name."
   ::= { zbrNetProtoSnmpv3Admin 1 }

zbrNetSnmpv3AdminAuthProtocol OBJECT-TYPE
   SYNTAX INTEGER {
      md5(1),
      sha(2)
   }
   MAX-ACCESS read-only
   STATUS current
   DESCRIPTION
   "Admin user's authentication protocol."
   ::= { zbrNetProtoSnmpv3Admin 2 }

zbrNetSnmpv3AdminPrivProtocol OBJECT-TYPE
   SYNTAX INTEGER {
      des(1),
      aes(2)
   }
   MAX-ACCESS read-only
   STATUS current
   DESCRIPTION
   "Admin user's privacy protocol."
   ::= { zbrNetProtoSnmpv3Admin 3 }

--=================================================================================================
--zebra.zbrInterfaces.zbrNetwork.zbrNetCommonNetworkSettings.zbrNetProtocols.zbrNetProtoSnmpv3.zbrNetProtoSnmpv3Monitor
--=================================================================================================

zbrNetSnmpv3MonitorName OBJECT-TYPE
   SYNTAX DisplayString (SIZE (0..32))
   MAX-ACCESS read-only
   STATUS current
   DESCRIPTION
   "Monitor user's name."
   ::= { zbrNetProtoSnmpv3Monitor 1 }

zbrNetSnmpv3MonitorAuthProtocol OBJECT-TYPE
   SYNTAX INTEGER {
      md5(1),
      sha(2)
   }
   MAX-ACCESS read-only
   STATUS current
   DESCRIPTION
   "Monitor user's authentication protocol."
   ::= { zbrNetProtoSnmpv3Monitor 2 }

zbrNetSnmpv3MonitorPrivProtocol OBJECT-TYPE
   SYNTAX INTEGER {
      des(1),
      aes(2)
   }
   MAX-ACCESS read-only
   STATUS current
   DESCRIPTION
   "Monitor user's privacy protocol."
   ::= { zbrNetProtoSnmpv3Monitor 3 }

--=================================================================================================
--zebra.zbrInterfaces.zbrNetwork.zbrNetCommonNetworkSettings.zbrNetJetAdmin
--=================================================================================================

zbrJetAdminEnabled OBJECT-TYPE
  SYNTAX INTEGER {
      no(1),
      yes(2)
   }
   MAX-ACCESS read-write
   STATUS current
   DESCRIPTION
    "Enable or disable jet admin support."
   ::= { zbrNetJetAdmin 1 }

--=================================================================================================
--zebra.zbrInterfaces.zbrNetwork.zbrNetCommonNetworkSettings.zbrNetDhcp
--=================================================================================================
zbrDhcpClientIdEnabled OBJECT-TYPE
    SYNTAX  INTEGER {
       no(1),
       yes(2),
       ifSpecified(255)
    }
    MAX-ACCESS read-write
    STATUS current
    DESCRIPTION
    "Enable/disable DHCP-CID on all interfaces.  You cannot set the value to
   ifSpecified but it is returned if the interfaces are not set to the same value (see ifdhcpCidTable)."
    ::= { zbrNetDhcp 1 }

zbrDhcpClientIdType OBJECT-TYPE
    SYNTAX  INTEGER {
       user-ascii(1),
       mac-address(2),
       user-hex(3),
       ifSpecified(255)
    }
    MAX-ACCESS read-write
    STATUS current
    DESCRIPTION
    "type of CID to use in DHCP request.
    (1)user-ascii: ascii character string.
    (2)mac-address: uses the hardware mac addresses, Prefix and Suffix fields are
          ignored.
    (3)user-hex: user string made up of hexadecimal number and letters characters
          where two characters represent 1 byte.
    (255)ifSpecified: not a valid set value.  Returned if the interfaces are not
          set to the same value (see ifdhcpCidTable).
    Maximum length of CID is 60 bytes.  For user type it is made up of the Prefix
          string + Suffix string.  If the combined length is too big the Suffix
          will be truncated to fix the length. "
    ::= { zbrNetDhcp 2 }

zbrDhcpClientIdPrefix OBJECT-TYPE
    SYNTAX  DisplayString (SIZE (0..22))
    MAX-ACCESS read-write
    STATUS current
    DESCRIPTION
    " Prefix portion of CID.  Length differs depending upon ClientIdType setting
     user-ascii- max 11 characters (extra characters are dropped).
     user-hex- max 22 characters (representing 11 bytes).
     mac-address- field not used.
     If the interfaces prefix strings are not the same then an empty string will be returned."
    ::= { zbrNetDhcp 3 }

zbrDhcpClientIdSuffix OBJECT-TYPE
    SYNTAX  DisplayString (SIZE (2..120))
    MAX-ACCESS read-write
    STATUS current
    DESCRIPTION
    "Suffix portion of CID.  Length differs depending upon ClientIdType setting
     user-ascii- min 2 character, max 60 characters (extra characters are dropped).
     User-hex- min 4 characters, max 120 characters (representing 60 bytes).
     mac-address- field not used.
     If a prefix is used then the suffix will be truncated to not exceed the max CID length.
     If the interfaces suffix strings are not the same then an empty string will be returned."
    ::= { zbrNetDhcp 4 }

zbrDhcpReceivedHostName OBJECT-TYPE
    SYNTAX OCTET STRING (SIZE (0..256))
    MAX-ACCESS read-only
    STATUS current
    DESCRIPTION
    "This is the host name given to us by the DHCP Server."
    ::= { zbrNetDhcp 5 }

zbrDhcpClientUserClassId OBJECT-TYPE
    SYNTAX DisplayString (SIZE (0..32))
    MAX-ACCESS read-write
    STATUS current
    DESCRIPTION
    "The DHCP user class class ID (DHCP option 77)."
    ::= { zbrNetDhcp 6 }
    
zbrDhcpClientVendorClassId OBJECT-TYPE
    SYNTAX DisplayString (SIZE (0..64))
    MAX-ACCESS read-write
    STATUS current
    DESCRIPTION
    "The DHCP vendor class ID (DHCP option 60)."
    ::= { zbrNetDhcp 7 }
    
zbrDhcpClientAutoProvisionEnable OBJECT-TYPE
  SYNTAX INTEGER {
      on(1),
      off(2)
   }
   MAX-ACCESS read-write
   STATUS current
   DESCRIPTION
   "Enable/disable the Zebra DHCP auto provision feature. This works in conjunction with DHCP options 60 & 43.
   See documentation for a full description of this feature."
    ::= { zbrNetDhcp 8 }

zbrDhcpNtpEnable OBJECT-TYPE
  SYNTAX INTEGER {
      on(1),
      off(2)
   }
   MAX-ACCESS read-write
   STATUS current
   DESCRIPTION
   "Enable/disable the DHCP client to request the IP addresses for NTP servers."
    ::= { zbrNetDhcp 9 }

zbrDhcpNtpReceivedServers OBJECT-TYPE
    SYNTAX DisplayString (SIZE (0..48))
    MAX-ACCESS read-only
    STATUS current
    DESCRIPTION
    "The list of NTP server's IP address(es) given to us by the DHCP Server."
    ::= { zbrNetDhcp 10 }
    
zbrDhcpDhcpv6Duid OBJECT-TYPE
    SYNTAX DisplayString (SIZE (0..355))
    MAX-ACCESS read-only
    STATUS current
    DESCRIPTION
    "Vendor unique identifier in hex for dhcp option 1, client identifier."
    ::= { zbrNetDhcp 11 }    

--=================================================================================================
--zebra.zbrInterfaces.zbrNetwork.zbrNetCommonNetworkSettings.zbrNetFirewall
--=================================================================================================
zbrFirewallWhitelistIn OBJECT-TYPE
    SYNTAX OCTET STRING (SIZE (0..256))
    MAX-ACCESS read-write
    STATUS current
    DESCRIPTION
    "List of comma separated individual IP Address Numbers, a range of IP Address numbers 
    specified by CIDR (Classless Inter-Domain Routin) notation, and a range of IP Address numbers 
    by specifying the starting and ending IP Address.  
    An empty value means all addresses are allowed."
    ::= { zbrNetFirewall 1 }
    
zbrFirewallProxy OBJECT-TYPE
    SYNTAX  OCTET STRING (SIZE (0..2048))
    MAX-ACCESS read-write
    STATUS current
    DESCRIPTION
    " Assigns the default proxy URL for any http conection."
    ::= { zbrNetFirewall 2 }

--=================================================================================================
--zebra.zbrInterfaces.zbrNetwork.zbrNetCommonNetworkSettings.zbrNetFirewall.zbrNetFirewallAuth
--=================================================================================================
zbrFirewallAuthenticationAdd OBJECT-TYPE
    SYNTAX  OCTET STRING (SIZE (0..2048))
    MAX-ACCESS read-write
    STATUS current
    DESCRIPTION
    " Allows the user to add a single server/username/password
     triplet into the default list of authentication entries for http connections. When the printer
     attempts to connect to the server the server may require some sort
     of HTTP authentication (e.g. digest, basic, NTLM, etc.). There may be multiple authentication
     requests along the route to the destination (e.g. a local server first requires HTTP
     authentication as well as on the remote server). For each HTTP authentication request
     received while attempting to connect, the printer will enumerate the authentication entries
     and attempt to satisfy the request with the username/password pair provided for the
     respective server. The server name in the entry is what determines which username/password
     pair should be used for which authentication request. Both dns names and IP addresses
     are acceptable. The server, username, and password are separated by a single space
     (not a tab or other white space character). The server name is the only required field.
     If no username is supplied, but a password is, there must be two spaces between the
     server and the password fields. If there is a username but no password, or simply just
     the servername, no space is required at the end of the entry."
    ::= { zbrNetFirewallAuth 1 }

zbrFirewallAuthenticationRemove OBJECT-TYPE
    SYNTAX  OCTET STRING (SIZE (0..2048))
    MAX-ACCESS read-write
    STATUS current
    DESCRIPTION
    " Allows the user to remove a single
     server/username/password triplet from the default list of authentication entries.
     To remove an entry only the server name is supplied however the entire entry
     will be removed. If an invalid entry is supplied no action is taken."
    ::= { zbrNetFirewallAuth 2 }

zbrFirewallAuthenticationEntries OBJECT-TYPE
    SYNTAX  DisplayString
    MAX-ACCESS read-only
    STATUS current
    DESCRIPTION
    " Lists the server names added to the default authentication
     entries list via zbrNetFirewall.zbrNetFirewallAuth.zbrFirewallAuthenticationAdd. Only the
     server names will be shown. The username and passwords will not be shown."
    ::= { zbrNetFirewallAuth 3 }

--=================================================================================================
--zebra.zbrInterfaces.zbrNetwork.zbrNetInterfaceSpecificSettings
--=================================================================================================

--=================================================================================================
--zebra.zbrInterfaces.zbrNetwork.zbrNetInterfaceSpecificSettings.zbrNetIfGeneral
--=================================================================================================
zbrNetIfGenNumEntries OBJECT-TYPE
   SYNTAX INTEGER
   MAX-ACCESS read-only
   STATUS current
   DESCRIPTION
   "The number of entries in the general table."
   ::= { zbrNetIfGeneral 1 }

zbrNetIfGenSettingsTable OBJECT-TYPE
   SYNTAX SEQUENCE OF ZbrNetIfGenSettingsEntry
   MAX-ACCESS not-accessible
   STATUS current
   DESCRIPTION
   "  Wireless, External Wired, Internal Wired"
   ::= { zbrNetIfGeneral 2 }

zbrNetIfGenSettingsEntry OBJECT-TYPE
   SYNTAX ZbrNetIfGenSettingsEntry
   MAX-ACCESS not-accessible
   STATUS current
   DESCRIPTION
   "An entry into General Network Specific Settings Table"
   INDEX { zbrNetIfGenInterfaceType }
   ::= { zbrNetIfGenSettingsTable 1 }

ZbrNetIfGenSettingsEntry ::=
   SEQUENCE {
      zbrNetIfGenInterfaceType
         INTEGER,
      zbrNetIfGenMacAddress
         DisplayString,
      zbrNetIfGenTablePointer
         OBJECT IDENTIFIER,
      zbrNetIfGenInterfaceRestoreDefaults
         INTEGER,
      zbrNetIfGenInstalled
         INTEGER
   }

zbrNetIfGenInterfaceType OBJECT-TYPE
   SYNTAX  INTEGER {
      external-wired(1),
      internal-wired(2),
      wireless(3)
   }
   MAX-ACCESS  read-only
   STATUS  current
   DESCRIPTION
    "A unique value for entry in the interface specific network settings.
        Its value ranges between 1 and the number of interfaces supported on
        this printer."
   ::= { zbrNetIfGenSettingsEntry 1 }

zbrNetIfGenMacAddress OBJECT-TYPE
   SYNTAX DisplayString
   MAX-ACCESS  read-only
   STATUS  current
   DESCRIPTION
    "The MAC Address of this interface."
   ::= { zbrNetIfGenSettingsEntry 2 }

zbrNetIfGenTablePointer OBJECT-TYPE
   SYNTAX OBJECT IDENTIFIER
   MAX-ACCESS  read-only
   STATUS  current
   DESCRIPTION
    "This OID points to the appropriate interface in the interfaces section of RFC1213.
        From there you can view more interface details."
   ::= { zbrNetIfGenSettingsEntry 3 }

zbrNetIfGenInterfaceRestoreDefaults OBJECT-TYPE
   SYNTAX INTEGER {
      no(1),
      yes(2)
   }
   MAX-ACCESS  read-write
   STATUS  current
   DESCRIPTION
    "Restore all the device specific settings on this interface to their default values.
        This will also reset the network stack."
   ::= { zbrNetIfGenSettingsEntry 4 }

zbrNetIfGenInstalled OBJECT-TYPE
   SYNTAX INTEGER {
      no(1),
      yes(2)
   }
   MAX-ACCESS  read-only
   STATUS  current
   DESCRIPTION
   "Is this interface option installed."
   ::= { zbrNetIfGenSettingsEntry 5 }

--=================================================================================================
--zebra.zbrInterfaces.zbrNetwork.zbrNetInterfaceSpecificSettings.zbrNetIfDhcp
--=================================================================================================

zbrNetIfDhcpNumEntries OBJECT-TYPE
   SYNTAX INTEGER
   MAX-ACCESS read-only
   STATUS current
   DESCRIPTION
   "The number of entries in any of the DHCP tables."
   ::= { zbrNetIfDhcp 1 }

zbrNetIfDhcpTable OBJECT-TYPE
   SYNTAX SEQUENCE OF ZbrNetIfDhcpEntry
   MAX-ACCESS not-accessible
   STATUS current
   DESCRIPTION
   "  Wireless, External Wired, Internal Wired"
   ::= { zbrNetIfDhcp 2 }

zbrNetIfDhcpEntry OBJECT-TYPE
   SYNTAX ZbrNetIfDhcpEntry
   MAX-ACCESS not-accessible
   STATUS current
   DESCRIPTION
   "An entry into DHCP CID Network Specific Settings Table"
   INDEX { zbrNetIfDhcpInterfaceType }
   ::= { zbrNetIfDhcpTable 1 }

   ZbrNetIfDhcpEntry ::=
      SEQUENCE {
         zbrNetIfDhcpInterfaceType
            INTEGER,
         zbrNetIfDhcpClientIdEnabled
            INTEGER,
         zbrNetIfDhcpClientIdType
            INTEGER,
         zbrNetIfDhcpClientIdPrefix
            DisplayString,
         zbrNetIfDhcpClientIdSuffix
            DisplayString,
         zbrNetIfDhcpClientArpVerifyEnabled
            INTEGER
      }

zbrNetIfDhcpInterfaceType OBJECT-TYPE
   SYNTAX INTEGER {
      external-wired(1),
      internal-wired(2),
      wireless(3)
   }
   MAX-ACCESS read-only
   STATUS current
   DESCRIPTION
   "A unique value for entry in the interface specific network settings.
   Its value ranges between 1 and the number of interfaces supported on
   this printer."
   ::= { zbrNetIfDhcpEntry 1 }

zbrNetIfDhcpClientIdEnabled OBJECT-TYPE
   SYNTAX INTEGER {
       no(1),
       yes(2)
   }
   MAX-ACCESS read-write
   STATUS current
   DESCRIPTION
   "Enable/disable DHCP-CID for this interface."
   ::= { zbrNetIfDhcpEntry 2 }

zbrNetIfDhcpClientIdType OBJECT-TYPE
   SYNTAX  INTEGER {
       user-ascii(1),
       mac-address(2),
       user-hex(3)
   }
   MAX-ACCESS read-write
   STATUS current
   DESCRIPTION
   "type of CID to use in DHCP request.
   (1)User-ascii: ascii character string.
   (2)Mac-address: uses the hardware mac addresses, Prefix and Suffix fields are
           ignored.
   (3)User-hex: user string made up of hexadecimal number and letters characters
           where two characters represent 1 byte.
    Maximum length of CID is 60 bytes.  For user type it is made up of the Prefix
           string + Suffix string.  If the combined length is too big the Suffix
           will be truncated to fix the length. "
   ::= { zbrNetIfDhcpEntry 3 }

zbrNetIfDhcpClientIdPrefix OBJECT-TYPE
   SYNTAX DisplayString (SIZE (0..22))
   MAX-ACCESS read-write
   STATUS current
   DESCRIPTION
   "
   user-ascii- max 11 characters (extra characters are dropped).
   user-hex- max 22 characters (representing 11 bytes).
   mac-address- field not used."
   ::= { zbrNetIfDhcpEntry 4 }

zbrNetIfDhcpClientIdSuffix OBJECT-TYPE
   SYNTAX DisplayString (SIZE (2..120))
   MAX-ACCESS read-write
   STATUS current
   DESCRIPTION
   "
   user-ascii- min 2 character, max 60 characters (extra characters are dropped).
   user-hex- min 4 characters, max 120 characters (representing 60 bytes).
   mac-address- field not used.

   If a prefix is used then the suffix will be truncated to not exceed the max CID length."
   ::= { zbrNetIfDhcpEntry 5 }

zbrNetIfDhcpClientArpVerifyEnabled OBJECT-TYPE
   SYNTAX INTEGER {
       no(1),
       yes(2)
   }
   MAX-ACCESS read-write
   STATUS current
   DESCRIPTION
   "Will the DHCP client do an ARP verification that the IP address is free before accepting the IP address."
   ::= { zbrNetIfDhcpEntry 6 }

--=================================================================================================
--zebra.zbrInterfaces.zbrNetwork.zbrNetInterfaceSpecificSettings.zbrNetIfTcp
--=================================================================================================

zbrNetIfTcpNumEntries OBJECT-TYPE
    SYNTAX  INTEGER
    MAX-ACCESS  read-only
    STATUS  current
    DESCRIPTION
    "The number of entries in the zbrNetIfTcp table."
    ::= { zbrNetIfTcp 1 }

zbrNetIfTcpSettingsTable OBJECT-TYPE
   SYNTAX SEQUENCE OF ZbrNetIfTcpSettingsEntry
   MAX-ACCESS not-accessible
   STATUS current
   DESCRIPTION
    "  Wireless, External Wired, Internal Wired"
   ::= { zbrNetIfTcp 2 }

zbrNetIfTcpSettingsEntry OBJECT-TYPE
   SYNTAX ZbrNetIfTcpSettingsEntry
   MAX-ACCESS not-accessible
   STATUS current
   DESCRIPTION
    "An entry into TCP/IP Network Specific Settings Table"
   INDEX { zbrNetIfTcpInterfaceType }
   ::= { zbrNetIfTcpSettingsTable 1 }

ZbrNetIfTcpSettingsEntry ::=
   SEQUENCE {
      zbrNetIfTcpInterfaceType
         INTEGER,
      zbrNetIfTcpIpAddr
         IpAddress,
      zbrNetIfTcpSubnetMask
         IpAddress,
      zbrNetIfTcpDefaultGateway
         IpAddress,
      zbrNetIfTcpIpAddressResolutionMode
         INTEGER,
      zbrNetIfTcpIpAddressResolutionTimeout
         INTEGER,
      zbrNetIfTcpConnectionTimeoutCheckingEnabled
         INTEGER,
      zbrNetIfTcpConnectionTimeoutValue
         INTEGER,
      zbrNetIfTcpArpInterval
         INTEGER,
      zbrNetIfTcpBaseRawPortNumber
         INTEGER,
      zbrNetIfTcpWinsAddressing
         INTEGER,
      zbrNetIfTcpWinsAddress
         IpAddress,
      zbrNetIfTcpIpAddressResolutionSource
         IpAddress,
      zbrNetIfTcpIpAddressResolutionModeUsed
         INTEGER,
      zbrNetIfTcpAlternateRawPortNumber
         INTEGER,
      zbrNetIfTcpJsonConfigPortNumber
         INTEGER
   }

zbrNetIfTcpInterfaceType OBJECT-TYPE
   SYNTAX  INTEGER {
      external-wired(1),
      internal-wired(2),
      wireless(3)
   }
   MAX-ACCESS  read-only
   STATUS  current
   DESCRIPTION
    "A unique value for entry in the interface specific network settings.
        Its value ranges between 1 and the number of interfaces supported on
        this printer."
   ::= { zbrNetIfTcpSettingsEntry 1 }

zbrNetIfTcpIpAddr OBJECT-TYPE
   SYNTAX IpAddress
   MAX-ACCESS read-write
   STATUS current
   DESCRIPTION
    "IP Address of this network interface."
   ::= { zbrNetIfTcpSettingsEntry 2 }

zbrNetIfTcpSubnetMask OBJECT-TYPE
   SYNTAX IpAddress
   MAX-ACCESS read-write
   STATUS current
   DESCRIPTION
    "Subnet Mask of this network interface."
   ::= { zbrNetIfTcpSettingsEntry 3 }

zbrNetIfTcpDefaultGateway OBJECT-TYPE
   SYNTAX IpAddress
   MAX-ACCESS read-write
   STATUS current
   DESCRIPTION
    "Default Gateway of this network interface."
   ::= { zbrNetIfTcpSettingsEntry 4 }

zbrNetIfTcpIpAddressResolutionMode OBJECT-TYPE
   SYNTAX  INTEGER {
      all-protocols(1),
      gleaning-only(2),
      rarp(3),
      bootp(4),
      dhcp(5),
      dhcp-and-bootp(6),
      permanent(7)
   }
   MAX-ACCESS  read-write
   STATUS  current
   DESCRIPTION
    "IP Protocol of this network interface."
   ::= { zbrNetIfTcpSettingsEntry 5 }

zbrNetIfTcpIpAddressResolutionTimeout OBJECT-TYPE
   SYNTAX INTEGER {
      no(1),
      yes(2),
      saved-ip(3)
   }
   MAX-ACCESS read-write
   STATUS current
   DESCRIPTION
    "After a specified time of being unable to obtain an ip address,
     this setting will tell the system if it should revert to a default address
     or continue seeking an IP address.  A value of saved-ip(3) will cause it to
     default to the last address stored in the printer.  This setting has no effect if the ip
     protocol is set to IP-PERM."
   ::= { zbrNetIfTcpSettingsEntry 6 }

zbrNetIfTcpConnectionTimeoutCheckingEnabled OBJECT-TYPE
   SYNTAX INTEGER {
      no(1),
      yes(2)
   }
   MAX-ACCESS read-write
   STATUS current
   DESCRIPTION
    "This setting controls whether it is possible for tcp connections
     to timeout.  If this is set to Yes(1), the timeout value setting will be
     used to determine how many seconds the connection needs to remain idle in
     order to be disconnected."
   ::= { zbrNetIfTcpSettingsEntry 7 }

zbrNetIfTcpConnectionTimeoutValue OBJECT-TYPE
   SYNTAX INTEGER
   MAX-ACCESS read-write
   STATUS current
   DESCRIPTION
    "The connection timeout value used in conjunction with the
     Connection Timeout Checking Enabled setting.  This value, in seconds, will
     tell when to terminate a TCP connection if the other side cannot be contacted."
   ::= { zbrNetIfTcpSettingsEntry 8 }

zbrNetIfTcpArpInterval OBJECT-TYPE
   SYNTAX INTEGER (0..30)
   MAX-ACCESS read-write
   STATUS current
   DESCRIPTION
    "The ARP interval in minutes.  A gratuitous ARP will be sent at this interval.
      Set to 0 to disable."
   ::= { zbrNetIfTcpSettingsEntry 9 }

zbrNetIfTcpBaseRawPortNumber   OBJECT-TYPE
   SYNTAX  INTEGER
   MAX-ACCESS  read-write
   STATUS  current
   DESCRIPTION
    "The TCP RAW port number to listen on for print jobs on.
     The default port is 9100 or 6101.  Setting this value to a TCP
     port that is in use by another TCP application will return an error."
   ::= { zbrNetIfTcpSettingsEntry 10 }

zbrNetIfTcpWinsAddressing OBJECT-TYPE
   SYNTAX INTEGER {
      dhcp(1),
      permanent(2)
   }
   MAX-ACCESS read-write
   STATUS current
   DESCRIPTION
    "The source of the WINS server address.
    If set to dhcp, the WINS address supplied with dhcp will be used.
    If it is set to permanent, it will use the stored WINS address."
   ::= { zbrNetIfTcpSettingsEntry 11 }

zbrNetIfTcpWinsAddress OBJECT-TYPE
   SYNTAX IpAddress
   MAX-ACCESS read-write
   STATUS current
   DESCRIPTION
    "The WINS server address.  If WinsAddressing is DHCP, then
     this will automatically be filled by the DHCP server.  Otherwise
     enter the ip address of the WINS server here."
   ::= { zbrNetIfTcpSettingsEntry 12 }

zbrNetIfTcpIpAddressResolutionSource OBJECT-TYPE
   SYNTAX IpAddress
   MAX-ACCESS read-only
   STATUS current
   DESCRIPTION
    "IP Address of the Server that assigned the IP Address of this network interface."
   ::= { zbrNetIfTcpSettingsEntry 13 }

zbrNetIfTcpIpAddressResolutionModeUsed OBJECT-TYPE
   SYNTAX  INTEGER {
      no-source(1),
      gleaning(2),
      rarp(3),
      bootp(4),
      dhcp(5),
      permanent(7)
   }
   MAX-ACCESS  read-only
   STATUS  current
   DESCRIPTION
    "Resolution mode used to assign the IP address of this network interface."
   ::= { zbrNetIfTcpSettingsEntry 14 }

zbrNetIfTcpAlternateRawPortNumber   OBJECT-TYPE
   SYNTAX  INTEGER
   MAX-ACCESS  read-write
   STATUS  current
   DESCRIPTION
   "An alternate TCP RAW port number to listen on for print jobs.
   The default port is 9100 or 6101.  Setting this value to a TCP
   port that is in use by another TCP application will return an error."
   ::= { zbrNetIfTcpSettingsEntry 15 }

zbrNetIfTcpJsonConfigPortNumber   OBJECT-TYPE
   SYNTAX  INTEGER
   MAX-ACCESS  read-write
   STATUS  current
   DESCRIPTION
   "A TCP port number on which to listen for JSON configuration packets.
   The default port is 9200.  Setting this value to a TCP port that is in use by
   another TCP application will return an error."
   ::= { zbrNetIfTcpSettingsEntry 16 }

--===========================
--zebra.zbrInterfaces.zbrInternalWired
--===========================

zbrIWiredActivityLed OBJECT-TYPE
   SYNTAX INTEGER {
      blink(1),
      solid(2)
   }
   MAX-ACCESS read-write
   STATUS current
   DESCRIPTION
   "Determines whether the network activity light blinks on activity or remains solid on link"
   ::= { zbrInternalWired 1 }

zbrIWiredEnable OBJECT-TYPE
  SYNTAX INTEGER {
      on(1),
      off(2)
   }
   MAX-ACCESS read-write
   STATUS current
   DESCRIPTION
   "Enable/disable the wired network interface."
   ::= { zbrInternalWired 2 }
   

zbrIWiredIpDnsDomainUserValue OBJECT-TYPE
   SYNTAX DisplayString
   MAX-ACCESS read-only
   STATUS current
   DESCRIPTION
   "This will display the value that the user has set to internal_wired.ip.dns.domain. Whether this value will be used will depend on the rules for internal_wired.ip.dns.domains."
   ::= { zbrInternalWired 4 }
   
zbrIWiredIpDnsServersUserValue OBJECT-TYPE
   SYNTAX DisplayString
   MAX-ACCESS read-only
   STATUS current
   DESCRIPTION
   "This will display the value that the user has set to internal_wired.ip.dns.servers. Whether this value will be used will depend on the rules for internal_wired.ip.dns.servers."
   ::= { zbrInternalWired 5 }
   
--===========================
--zebra.zbrInterfaces.zbrInternalWired.zbrIWiredIpv6
--===========================

zbrIWiredIpv6AddrType OBJECT-TYPE
   SYNTAX INTEGER {
      static(1),
      auto(2)
   }
   MAX-ACCESS read-write
   STATUS current
   DESCRIPTION
   "Control how the interface will get IPv6 address(es)."
   ::= { zbrIWiredIpv6 1 }
   
zbrIWiredIpv6Addresses OBJECT-TYPE
   SYNTAX DisplayString (SIZE (0..509))
   MAX-ACCESS read-only
   STATUS current
   DESCRIPTION
   "' when no address has been set."
   ::= { zbrIWiredIpv6 2 }
   
   
zbrIWiredIpv6Gateways OBJECT-TYPE
   SYNTAX DisplayString (SIZE (0..509))
   MAX-ACCESS read-only
   STATUS current
   DESCRIPTION
   "List of known gateways in use by the printer. Max list of 10."
   ::= { zbrIWiredIpv6 3 }   
   
--===========================
--zebra.zbrInterfaces.zbrInternalWired.zbrIWiredIpv6.zbrIWiredIpv6Dhcp
--===========================
zbrIWiredIpv6DhcpLeaseLength OBJECT-TYPE
   SYNTAX Unsigned32
   MAX-ACCESS read-only
   STATUS current
   DESCRIPTION
   "IPv6 DHCP lease time in seconds of preferred life."
   ::= { zbrIWiredIpv6Dhcp 1 }

zbrIWiredIpv6DhcpLeaseTimeLeft OBJECT-TYPE
   SYNTAX Unsigned32
   MAX-ACCESS read-only
   STATUS current
   DESCRIPTION
   "IPv6 DHCP lease time left in seconds of preferred life."
   ::= { zbrIWiredIpv6Dhcp 2 }

zbrIWiredIpv6DhcpLeaseLastAttempt OBJECT-TYPE
   SYNTAX Unsigned32
   MAX-ACCESS read-only
   STATUS current
   DESCRIPTION
   "IPv6 DHCP lease last attemp time in UNIX timestamp."
   ::= { zbrIWiredIpv6Dhcp 3 }

zbrIWiredIpv6DhcpOption39Enable OBJECT-TYPE
   SYNTAX INTEGER {
      on(1),
      off(2)
   }
   MAX-ACCESS read-write
   STATUS current
   DESCRIPTION
   "
   Control the inclusion of option39 in DHCPv6 communication."
   ::= { zbrIWiredIpv6Dhcp 4 }

zbrIWiredIpv6DhcpOption39Format OBJECT-TYPE
   SYNTAX DisplayString (SIZE (0..127))
   MAX-ACCESS read-write
   STATUS current
   DESCRIPTION
   "
   The format string that determines the value for option39 used in DHCPv6 packets."
   ::= { zbrIWiredIpv6Dhcp 5 }

zbrIWiredIpv6DhcpOption39Value OBJECT-TYPE
   SYNTAX DisplayString (SIZE (0..127))
   MAX-ACCESS read-only
   STATUS current
   DESCRIPTION
   "
   The processed value derived from option39_format field. Will be used as the DHCPv6 option39 value."
   ::= { zbrIWiredIpv6Dhcp 6 }

zbrIWiredIpv6DhcpOption39Fqdn OBJECT-TYPE
   SYNTAX DisplayString (SIZE (0..127))
   MAX-ACCESS read-only
   STATUS current
   DESCRIPTION
   "
   The fully qualified domain name of the printer as given by the DHCPv6 server."
   ::= { zbrIWiredIpv6Dhcp 7 }

--===========================
--zebra.zbrInterfaces.zbrInternalWired.zbrIWiredIpv6.zbrIWiredIpv6Static
--===========================
   
zbrIWiredIpv6StaticAddresses OBJECT-TYPE
   SYNTAX DisplayString (SIZE (0..152))
   MAX-ACCESS read-write
   STATUS current
   DESCRIPTION
   "' when no static address has been set."
   ::= { zbrIWiredIpv6Static 1 }
   
zbrIWiredIpv6StaticGateways OBJECT-TYPE
   SYNTAX DisplayString (SIZE (0..152))
   MAX-ACCESS read-write
   STATUS current
   DESCRIPTION
   "IPv6 gateways(s) to be used when address_type is static. Up to 3 gateways can be set."
   ::= { zbrIWiredIpv6Static 2 }   

--===========================
--zebra.zbrInterfaces.zbrInternalWired.zbrIWired8021x
--===========================
zbrIWiredSecurity OBJECT-TYPE
   SYNTAX INTEGER {
      none(1),
      peap(2),
      eap-tls(3),
      eap-ttls(4)
   }
   MAX-ACCESS read-write
   STATUS current
   DESCRIPTION
   "Control 8021x wired usage and protocol"
   ::= { zbrIWired8021x 1 }

zbrIWired8021xUserName OBJECT-TYPE
   SYNTAX DisplayString (SIZE (0..64))
   MAX-ACCESS read-write
   STATUS current
   DESCRIPTION
   "username for securities that use it."
   ::= { zbrIWired8021x 2 }

zbrIWired8021xPassword OBJECT-TYPE
   SYNTAX DisplayString (SIZE (0..32))
   MAX-ACCESS read-write
   STATUS current
   DESCRIPTION
   "password for securities that use one.  A get returns '*' not the current value."
   ::= { zbrIWired8021x 3 }

zbrIWired8021xPrivateKeyPassword OBJECT-TYPE
   SYNTAX DisplayString (SIZE (0..32))
   MAX-ACCESS read-write
   STATUS current
   DESCRIPTION
   "Private key password for securities that use one.  A get returns '*' not the current value."
   ::= { zbrIWired8021x 4 }

zbrIWired8021xTtlsTunnel OBJECT-TYPE
   SYNTAX INTEGER {
      pap(1),
      chap(2),
      mschap(3),
      mschapv2(4)
   }
   MAX-ACCESS read-write
   STATUS current
   DESCRIPTION
   "Tunnel protocol to use when using EAP-TTLS"
   ::= { zbrIWired8021x 5 }

zbrIWired8021xValidatePeapServerCertificate OBJECT-TYPE
   SYNTAX  INTEGER {
      on(1),
      off(2)
   }
   MAX-ACCESS read-write
   STATUS current
   DESCRIPTION
   "Control the check of the server certificate when using PEAP security"
   ::= { zbrIWired8021x 6 }

zbrIWired8021xPeapAnonymousIdentity OBJECT-TYPE
   SYNTAX DisplayString (SIZE (0..32))
   MAX-ACCESS read-write
   STATUS current
   DESCRIPTION
   "anonymous identity to be used with PEAP."
   ::= { zbrIWired8021x 7 }

zbrIWired8021xTtlsAnonymousIdentity OBJECT-TYPE
   SYNTAX DisplayString (SIZE (0..32))
   MAX-ACCESS read-write
   STATUS current
   DESCRIPTION
   "anonymous identity to be used with TTLS."
   ::= { zbrIWired8021x 8 }
   
--=================================================================================================
--zebra.zbrJobLogging
--=================================================================================================

zbrOutputTotalJobsLogged OBJECT-TYPE
    SYNTAX  INTEGER
    MAX-ACCESS  read-only
    STATUS  current
    DESCRIPTION
    "The total number of jobs printed by the printer since the
    print server was powered on. "
    ::= { zbrJobLogging 1 }

zbrOutputNumLogEntries OBJECT-TYPE
    SYNTAX  INTEGER
    MAX-ACCESS  read-only
    STATUS  current
    DESCRIPTION
    "The number of job log entries."
    ::= { zbrJobLogging 2 }

zbrOutputJobLogTable OBJECT-TYPE
    SYNTAX  SEQUENCE OF ZbrOutputJobLogEntry
    MAX-ACCESS  not-accessible
    STATUS  current
    DESCRIPTION
    "A 2 dimensional list of Job log entries indexed by the output port
    number and the log entry index (1 through outputNumJobLogEntries).
    The number of entries per output port is given by the value of
    outputNumJobLogEntries."
    ::= { zbrJobLogging 3 }

zbrOutputJobLogEntry OBJECT-TYPE
    SYNTAX  ZbrOutputJobLogEntry
    MAX-ACCESS  not-accessible
    STATUS  current
    DESCRIPTION
    "A Job log entry."
    INDEX   { zbrOutputJobLogIndex }
    ::= { zbrOutputJobLogTable 1 }

ZbrOutputJobLogEntry ::=
    SEQUENCE {
        zbrOutputJobLogInformation
            DisplayString,
        zbrOutputJobLogTime
            DisplayString,
        zbrOutputJobLogIndex
            INTEGER
    }

zbrOutputJobLogInformation OBJECT-TYPE
    SYNTAX  DisplayString (SIZE (0..100))
    MAX-ACCESS  read-only
    STATUS  current
    DESCRIPTION
    "A textual description of print job information.
    The protocol, source, and file size are always included.
    Other information such as File Server, Queue, File Name, etc
    will be included if available."
    ::= { zbrOutputJobLogEntry 1 }

zbrOutputJobLogTime OBJECT-TYPE
    SYNTAX  DisplayString (SIZE (0..50))
    MAX-ACCESS  read-only
    STATUS  current
    DESCRIPTION
    "A string indicating the elapsed time since the last job was
    printed. Reported in form X hours X minutes X seconds."
    ::= { zbrOutputJobLogEntry 2 }

zbrOutputJobLogIndex OBJECT-TYPE
    SYNTAX  INTEGER (0..2147483647)
    MAX-ACCESS  read-only
    STATUS  current
    DESCRIPTION
    "A unique value for each log entry."
    ::= { zbrOutputJobLogEntry 3 }


--=================================================================================================
--zebra.zbrDataCapture.zbrDCapChannel1
--=================================================================================================
zbrDCapChan1Port OBJECT-TYPE
    SYNTAX INTEGER {
        off(1),
        serial(2),
        usb(3),
        bt(4),
        parallel(5)
    }
    MAX-ACCESS  read-write
    STATUS  current
    DESCRIPTION
    "A value indicating the data port to capture data from."
    ::= { zbrDCapChannel1 1 }
zbrDCapChan1Delimiter OBJECT-TYPE
    SYNTAX  OCTET STRING (SIZE (0..256))
    MAX-ACCESS  read-write
    STATUS  current
    DESCRIPTION
    "A string indicating when to copy captured data the data OID.
    In the string, text in the format \###, where ### are 3 octal numbers, is replaced with a single
    byte of that value.  To get a binary zero you would send the value of \000.
    The maximum length of a delimiter is 64 bytes, but listed as 256 to allow for binary zeros."
    ::= { zbrDCapChannel1 2 }
zbrDCapChan1MaxLength OBJECT-TYPE
    SYNTAX  INTEGER (0..3000)
    MAX-ACCESS  read-write
    STATUS  current
    DESCRIPTION
    "A length indicating when to copy captured data the data OID if the delimiter has not been seen yet."
    ::= { zbrDCapChannel1 3 }
zbrDCapChan1Count OBJECT-TYPE
    SYNTAX  INTEGER
    MAX-ACCESS  read-only
    STATUS  current
    DESCRIPTION
    "A value indicating the number of data captures that have occurred since the printer was powered on."
    ::= { zbrDCapChannel1 4 }

--=================================================================================================
--zebra.zbrDataCapture.zbrDCapChannel1.zbrDCapChan1Data
--=================================================================================================
zbrDCapChan1DataRaw OBJECT-TYPE
    SYNTAX  DisplayString
    MAX-ACCESS  read-only
    STATUS  current
    DESCRIPTION
    "A string containing the last data captured on this channnel.
    Any binary zeros in the data stream will be replaced with the escaped representation of NULL (\000)."
    ::= { zbrDCapChan1Data 1 }
zbrDCapChan1DataMime OBJECT-TYPE
    SYNTAX  DisplayString
    MAX-ACCESS  read-only
    STATUS  current
    DESCRIPTION
    "The last data captured on this channnel presented in mime format."
    ::= { zbrDCapChan1Data 2 }

--=================================================================================================
--zebra.zbrWeblink
--=================================================================================================
zbrWeblinkEnable OBJECT-TYPE
   SYNTAX  INTEGER {
       no(1),
       yes(2)    }
    MAX-ACCESS read-only
   STATUS current
   DESCRIPTION
   "Indicates if any of the available Weblink connections are enabled."
   ::= { zbrWeblink 1 }

zbrWeblinkPrinterResetRequired OBJECT-TYPE
   SYNTAX  INTEGER {
       no(1),
       yes(2)    }
    MAX-ACCESS read-only
   STATUS current
   DESCRIPTION
   "Indicates if any of the Weblink settings have changed."
   ::= { zbrWeblink 2 }

zbrWeblinkRestoreDefaults OBJECT-TYPE
   SYNTAX  INTEGER {
       no(1),
       yes(2)    }
    MAX-ACCESS read-write
   STATUS current
   DESCRIPTION
   "Defaults, and saves, the weblink branch settings"
   ::= { zbrWeblink 3 }

--=================================================================================================
--zebra.zbrWeblinkLogging
--=================================================================================================
zbrWeblinkLoggingMaxEntries OBJECT-TYPE
   SYNTAX INTEGER (0..10000)
   MAX-ACCESS read-write
   STATUS current
   DESCRIPTION
   "The maximum number of entries in the log. Setting this value to 0 disables logging."
   ::= { zbrWeblinkLogging 1 }

zbrWeblinkLoggingClear OBJECT-TYPE
   SYNTAX  INTEGER {
       no(1),
       yes(2)    }
    MAX-ACCESS read-write
   STATUS current
   DESCRIPTION
   "Clears the Weblink log when set to yes(2)."
   ::= { zbrWeblinkLogging 2 }

--=================================================================================================
--zebra.zbrWeblinkCloudConnect
--=================================================================================================
zbrWeblinkCloudConnEnable OBJECT-TYPE
   SYNTAX  INTEGER {
      on(1),
      off(2)
   }
   MAX-ACCESS read-write
   STATUS current
   DESCRIPTION
   "State of Cloud Connect feature."
   ::= { zbrWeblinkCloudConnect 1 }

zbrWeblinkCloudConnConnect OBJECT-TYPE
   SYNTAX  INTEGER {
       disconnect(1),
       connect(2)    }
   MAX-ACCESS read-write
   STATUS current
   DESCRIPTION
   "Start/stop the connection to the Cloud Connect Server.  
   Use zbrWeblinkCloudConnStatus for the connection state as this always reports as disconnected."
   ::= { zbrWeblinkCloudConnect 2 }

zbrWeblinkCloudConnStatus OBJECT-TYPE
    SYNTAX  DisplayString (SIZE (0..20))
    MAX-ACCESS read-only
    STATUS current
    DESCRIPTION
    "Status of the connection to the Cloud Connect Server"
    ::= { zbrWeblinkCloudConnect 3 }

zbrWeblinkCloudConnConnectionKey OBJECT-TYPE
    SYNTAX  DisplayString (SIZE (10))
    MAX-ACCESS read-only
    STATUS current
    DESCRIPTION
    "Printer generated connection key used to claim the printer from the Cloud Connect Server."
    ::= { zbrWeblinkCloudConnect 4 }

zbrWeblinkCloudConnConfigurationKey OBJECT-TYPE
    SYNTAX  DisplayString (SIZE (10))
    MAX-ACCESS read-only
    STATUS current
    DESCRIPTION
    "Server generated configuration key used for user to accept configuration from their server via the Cloud Connect Server."
    ::= { zbrWeblinkCloudConnect 5 }

zbrWeblinkCloudConnConfigurationConfirmation OBJECT-TYPE
   SYNTAX  INTEGER {
       none(1),
       accept(2),
       reject(3),
       complete(4)    }
   MAX-ACCESS read-write
   STATUS current
   DESCRIPTION
   "Control the configuration acceptance steps.  'Accept'/'reject' set by user, 'complete' set by the server."
   ::= { zbrWeblinkCloudConnect 6 }

--=================================================================================================
--zebra.zbrWeblink.zbrWeblinkConn1
--=================================================================================================
zbrWeblinkConn1Location OBJECT-TYPE
    SYNTAX  OCTET STRING (SIZE (0..2048))
    MAX-ACCESS read-write
    STATUS current
    DESCRIPTION
    " Assigns the URL of the server for
       this connection. The URL must follow the URL rules for the HTTP[S] protocol outlined in
       RFC2396 (http://www.ietf.org/rfc/rfc2396.txt). When this setting's value changes
       zbrWeblinkPrinterResetRequired will be set to yes to indicate that the printer must
       be reset for this setting to take effect"
    ::= { zbrWeblinkConn1 1 }

zbrWeblinkConn1RetryInterval OBJECT-TYPE
    SYNTAX  INTEGER  (1..600)
    MAX-ACCESS  read-write
    STATUS  current
    DESCRIPTION
    " The number of seconds between attempts to connect to the
    server URL provided in zbrWeblinkConn1Location. If an attempt is unsucessful or the
    connection is lost, the printer will wait 'zbrWeblinkConn1RetryInterval' seconds before
    attempting to connect again. If this value is changed you need to reset the printer for it to take effect."
    ::= { zbrWeblinkConn1 2 }

zbrWeblinkConn1Proxy OBJECT-TYPE
    SYNTAX  OCTET STRING (SIZE (0..2048))
    MAX-ACCESS read-write
    STATUS current
    DESCRIPTION
    " Assigns the URL of the proxy for this connection."
    ::= { zbrWeblinkConn1 3 }

zbrWeblinkConn1MaximumSimultaneousConnections OBJECT-TYPE
    SYNTAX INTEGER (1..100)
    MAX-ACCESS  read-write
    STATUS  current
    DESCRIPTION
    " Via the main connection (the original connection initiated by the printer to the remote
    server), the remote server can request that additional connections from the printer be initiated
    (e.g. a connection that supports only JSON SGDs, one that only allows firmware downloads, etc.).
    This indicates the maximum number of those simultaneous connections that can be initiated by the printer.
    The server is free to request as many as it thinks it needs, but the printer will prevent more than N number
    of connections, where N is the value. An error will be sent back to the remote server over the
    original connection to indicate that the maximum has been reached."
    ::= { zbrWeblinkConn1 4 }

zbrWeblinkConn1NumConnections OBJECT-TYPE
    SYNTAX INTEGER (0..100)
    MAX-ACCESS  read-only
    STATUS  current
    DESCRIPTION
    " The current number of established connections."
    ::= { zbrWeblinkConn1 5 }

zbrWeblinkConn1RetryIntervalRandomMax OBJECT-TYPE
    SYNTAX  INTEGER  (0..600)
    MAX-ACCESS  read-write
    STATUS  current
    DESCRIPTION
    " The maximum number of seconds between attempts to connect to the
    server URL provided in zbrWeblinkConn1Location. If an attempt is unsuccessful or the connection is lost, 
    the printer will wait a random number of seconds between 0 and this value to attempting to connect again.  
    If the value is 0 then it will wait 'zbrWeblinkConn1RetryInterval' seconds before attempting to connect again. 
    If this value is changed you need to reset the printer for it to take effect."
    ::= { zbrWeblinkConn1 6 }

--=================================================================================================
--zebra.zbrWeblink.zbrWeblinkConn1.zbrWeblinkConn1Authentication
--=================================================================================================
zbrWeblinkConn1AuthenticationAdd OBJECT-TYPE
    SYNTAX  OCTET STRING (SIZE (0..2048))
    MAX-ACCESS read-write
    STATUS current
    DESCRIPTION
    " Allows the user to add a single server/username/password
     triplet into the list of authentication entries. When the printer attempts to connect to the
     server (url specified in zbrWeblink.zbrWeblinkConn1Location) the server may require some sort
     of HTTP authentication (e.g. digest, basic, NTLM, etc.). There may be multiple authentication
     requests along the route to the destination (e.g. a local server first requires HTTP
     authentication as well as on the remote server). For each HTTP authentication request
     received while attempting to connect, the printer will enumerate the authentication entries
     and attempt to satisfy the request with the username/password pair provided for the
     respective server. The server name in the entry is what determines which username/password
     pair should be used for which authentication request. Both dns names and IP addresses
     are acceptable. The server, username, and password are separated by a single space
     (not a tab or other white space character). The server name is the only required field.
     If no username is supplied, but a password is, there must be two spaces between the
     server and the password fields. If there is a username but no password, or simply just
     the servername, no space is required at the end of the entry."
    ::= { zbrWeblinkConn1Authentication 1 }

zbrWeblinkConn1AuthenticationRemove OBJECT-TYPE
    SYNTAX  OCTET STRING (SIZE (0..2048))
    MAX-ACCESS read-write
    STATUS current
    DESCRIPTION
    " Allows the user to remove a single
     server/username/password triplet from the list of authentication entries.
     To remove an entry only the server name is supplied however the entire entry
     will be removed. If an invalid entry is supplied no action is taken."
    ::= { zbrWeblinkConn1Authentication 2 }

zbrWeblinkConn1AuthenticationEntries OBJECT-TYPE
    SYNTAX  DisplayString
    MAX-ACCESS read-only
    STATUS current
    DESCRIPTION
    " Lists the server names added to the authentication
     entries list via zbrWeblinkConn1.zbrWeblinkConn1Authentication. Only the server names
     will be shown. The username and passwords will not be shown."
    ::= { zbrWeblinkConn1Authentication 3 }
--=================================================================================================
--zebra.zbrWeblink.zbrWeblinkConn1.zbrWeblinkConn1Test
--=================================================================================================
zbrWeblinkConn1TestLocation OBJECT-TYPE
    SYNTAX  OCTET STRING (SIZE (0..2048))
    MAX-ACCESS read-write
    STATUS current
    DESCRIPTION
    " Determines when the test connection should be attempted.
       This is meant to assist users in debugging their printer's connection to remote servers."
    ::= { zbrWeblinkConn1Test 1 }

zbrWeblinkConn1TestOn OBJECT-TYPE
    SYNTAX INTEGER {
        off(1),
        failure(2),
        interval(3),
        both(4)
    }
    MAX-ACCESS  read-write
    STATUS  current
    DESCRIPTION
    " Determines when the
    test connection should be attempted. This is meant to assist users in debugging their printer's
    connection to remote servers."
    ::= { zbrWeblinkConn1Test 2 }

zbrWeblinkConn1TestRetryInterval OBJECT-TYPE
    SYNTAX  INTEGER (1..1800)
    MAX-ACCESS  read-write
    STATUS  current
    DESCRIPTION
    " Determines how often, in seconds, a connection to
    the test.location URL should be attempted. This setting is only applicable when the
    test.test_on SGD is set to interval or both."
    ::= { zbrWeblinkConn1Test 3 }

--=================================================================================================
--zebra.zbrWeblink.zbrWeblinkConn2
--=================================================================================================
zbrWeblinkConn2Location OBJECT-TYPE
    SYNTAX  OCTET STRING (SIZE (0..2048))
    MAX-ACCESS read-write
    STATUS current
    DESCRIPTION
    " Assigns the URL of the server for this connection. The URL must
     follow the URL rules for the HTTP[S] protocol outlined in
     RFC2396 (http://www.ietf.org/rfc/rfc2396.txt). When this setting's value changes
     zbrWeblinkPrinterResetRequired will be set to yes to indicate that the printer must
     be reset for this setting to take effect."
    ::= { zbrWeblinkConn2 1 }

zbrWeblinkConn2RetryInterval OBJECT-TYPE
    SYNTAX  INTEGER (1..600)
    MAX-ACCESS  read-write
    STATUS  current
    DESCRIPTION
    " The number of seconds between attempts to connect to the
    server URL provided in zbrWeblinkConn2Location. If an attempt is unsucessful or the
    connection is lost, the printer will wait 'zbrWeblinkConn2RetryInterval' seconds before
    attempting to connect again. If this value is changed you need to reset the printer for it to take effect."
    ::= { zbrWeblinkConn2 2 }

zbrWeblinkConn2Proxy OBJECT-TYPE
    SYNTAX  OCTET STRING (SIZE (0..2048))
    MAX-ACCESS read-write
    STATUS current
    DESCRIPTION
    " Assigns the URL of the proxy for this connection."
    ::= { zbrWeblinkConn2 3 }

zbrWeblinkConn2MaximumSimultaneousConnections OBJECT-TYPE
    SYNTAX INTEGER (1..100)
    MAX-ACCESS  read-write
    STATUS  current
    DESCRIPTION
    " Via the main connection (the original connection initiated by the printer to the remote
    server), the remote server can request that additional connections from the printer be initiated
    (e.g. a connection that supports only JSON SGDs, one that only allows firmware downloads, etc.).
    This indicates the maximum number of those simultaneous connections that can be initiated by the printer.
    The server is free to request as many as it thinks it needs, but the printer will prevent more than N number
    of connections, where N is the value. An error will be sent back to the remote server over the
    original connection to indicate that the maximum has been reached."
    ::= { zbrWeblinkConn2 4 }

zbrWeblinkConn2NumConnections OBJECT-TYPE
    SYNTAX INTEGER (0..100)
    MAX-ACCESS  read-only
    STATUS  current
    DESCRIPTION
    " The current number of established connections."
    ::= { zbrWeblinkConn2 5 }

zbrWeblinkConn2RetryIntervalRandomMax OBJECT-TYPE
    SYNTAX  INTEGER  (0..600)
    MAX-ACCESS  read-write
    STATUS  current
    DESCRIPTION
    " The maximum number of seconds between attempts to connect to the
    server URL provided in zbrWeblinkConn2Location. If an attempt is unsuccessful or the connection is lost, 
    the printer will wait a random number of seconds between 0 and this value to attempting to connect again.  
    If the value is 0 then it will wait 'zbrWeblinkConn2RetryInterval' seconds before attempting to connect again. 
    If this value is changed you need to reset the printer for it to take effect."
    ::= { zbrWeblinkConn2 6 }

--=================================================================================================
--zebra.zbrWeblink.zbrWeblinkConn2.zbrWeblinkConn2Authentication
--=================================================================================================
zbrWeblinkConn2AuthenticationAdd OBJECT-TYPE
    SYNTAX  OCTET STRING (SIZE (0..2048))
    MAX-ACCESS read-write
    STATUS current
    DESCRIPTION
    " Allows the user to add a single server/username/password
    triplet into the list of authentication entries. When the printer attempts to connect to the
    server (url specified in zbrWeblink.zbrWeblinkConn2Location) the server may require some
    sort of HTTP authentication (e.g. digest, basic, NTLM, etc.). There may be multiple
    authentication requests along the route to the destination (e.g. a local server first
    requires HTTP authentication as well as on the remote server). For each HTTP authentication
    request received while attempting to connect, the printer will enumerate the authentication
    entries and attempt to satisfy the request with the username/password pair provided for
    the respective server. The server name in the entry is what determines which username/password
    pair should be used for which authentication request. Both dns names and IP addresses
    are acceptable. The server, username, and password are separated by a single space (not a
    tab or other white space character). The server name is the only required field. If no
    username is supplied, but a password is, there must be two spaces between the server and
    the password fields. If there is a username but no password, or simply just the
    servername, no space is required at the end of the entry."
    ::= { zbrWeblinkConn2Authentication 1 }

zbrWeblinkConn2AuthenticationRemove OBJECT-TYPE
    SYNTAX  OCTET STRING (SIZE (0..2048))
    MAX-ACCESS read-write
    STATUS current
    DESCRIPTION
    " Allows the user to remove a single
     server/username/password triplet from the list of authentication entries. To
     remove an entry only the server name is supplied however the entire entry will be
     removed. If an invalid entry is supplied no action is taken."
    ::= { zbrWeblinkConn2Authentication 2 }

zbrWeblinkConn2AuthenticationEntries OBJECT-TYPE
    SYNTAX  DisplayString
    MAX-ACCESS read-only
    STATUS current
    DESCRIPTION
    " Lists the server names added to the authentication
     entries list via zbrWeblinkConn2.zbrWeblinkConn2Authentication. Only the server
     names will be shown. The username and passwords will not be shown."
    ::= { zbrWeblinkConn2Authentication 3 }

--=================================================================================================
--zebra.zbrWeblink.zbrWeblinkConn2.zbrWeblinkConn2Test
--=================================================================================================
zbrWeblinkConn2TestLocation OBJECT-TYPE
    SYNTAX  OCTET STRING (SIZE (0..2048))
    MAX-ACCESS read-write
    STATUS current
    DESCRIPTION
    " Determines when the test connection should be attempted.
     This is meant to assist users in debugging their printer's connection to remote servers."
    ::= { zbrWeblinkConn2Test 1 }

zbrWeblinkConn2TestOn OBJECT-TYPE
    SYNTAX INTEGER {
        off(1),
        failure(2),
        interval(3),
        both(4)
    }
    MAX-ACCESS  read-write
    STATUS  current
    DESCRIPTION
    " Determines when the test
    connection should be attempted. This is meant to assist users in debugging their printer's
    connection to remote servers."
    ::= { zbrWeblinkConn2Test 2 }

zbrWeblinkConn2TestRetryInterval OBJECT-TYPE
    SYNTAX  INTEGER (1..1800)
    MAX-ACCESS  read-write
    STATUS  current
    DESCRIPTION
    " Determines how often, in seconds, a
    connection to the test.location URL should be attempted. This setting is
    only applicable when the test.test_on SGD is set to interval or both."
    ::= { zbrWeblinkConn2Test 3 }

--====================================================================================
-- zebra.zbrBasicInterpreter
--====================================================================================

zbrZbiState OBJECT-TYPE
    SYNTAX  INTEGER {
        stopped(1),
        running(2)
    }
    MAX-ACCESS  read-only
    STATUS  current
    DESCRIPTION
    " Current State of ZBI."
    ::= { zbrBasicInterpreter 1 }

zbrZbiVersion OBJECT-TYPE
    SYNTAX  DisplayString
    MAX-ACCESS  read-only
    STATUS  current
    DESCRIPTION
    " ZBI Version"
    ::= { zbrBasicInterpreter 2 }

zbrZbiLastError OBJECT-TYPE
    SYNTAX  DisplayString
    MAX-ACCESS  read-only
    STATUS  current
    DESCRIPTION
    " The Last Error Received by ZBI, or null if none."
    ::= { zbrBasicInterpreter 3 }

zbrZbiResellerKey OBJECT-TYPE
    SYNTAX  DisplayString
    MAX-ACCESS  read-write
    STATUS  current
    DESCRIPTION
    " The
     reseller key used to encrypt BAE ZBI files. This value should
     only be set. It returns '*' when read."
    ::= { zbrBasicInterpreter 4 }

zbrZbiLicense OBJECT-TYPE
    SYNTAX  DisplayString
    MAX-ACCESS  read-only
    STATUS  current
    DESCRIPTION
    " Returns ENABLED if a valid ZBI license is present,
       DISALBED otherwise."
    ::= { zbrBasicInterpreter 5 }

zbrZbiRunningProgramName OBJECT-TYPE
    SYNTAX  DisplayString
    MAX-ACCESS  read-only
    STATUS  current
    DESCRIPTION
    " The name of the currently running
     ZBI program, if known, otherwise null."
    ::= { zbrBasicInterpreter 6 }

zbrZbiProgramListSet OBJECT-TYPE
   SYNTAX INTEGER {
        up(1),
        down(2),
        fill(3),
        execute(4)
    }
   MAX-ACCESS read-write
   STATUS current
   DESCRIPTION
   " Up,Down,Fill and Execute
   .bas files on the E drive."
   ::= { zbrBasicInterpreter 7 }

zbrZbiProgramListGet OBJECT-TYPE
   SYNTAX DisplayString  (SIZE (0..255))
   MAX-ACCESS read-only
   STATUS current
   DESCRIPTION
   " Get the current .bas filename on the E drive."
   ::= { zbrBasicInterpreter 8 }

zbrZbiEnable OBJECT-TYPE
  SYNTAX INTEGER {
      on(1),
      off(2)
   }
   MAX-ACCESS read-write
   STATUS current
   DESCRIPTION
   "Enable/disable ZBI"
   ::= { zbrBasicInterpreter 9 }

--====================================================================================
-- zebra.zbrBasicInterpreter.zbrZbiStartInfo
--====================================================================================

zbrZbiStartInfoFileName OBJECT-TYPE
    SYNTAX  DisplayString  (SIZE (0..16))
    MAX-ACCESS  read-write
    STATUS  current
    DESCRIPTION
    " Name of the file to run.  Must already be
   present on the printer."
    ::= { zbrZbiStartInfo 1 }

zbrZbiStartInfoMemoryAlloc OBJECT-TYPE
    SYNTAX  INTEGER
    MAX-ACCESS  read-only
    STATUS  current
    DESCRIPTION
    " The current amout of memory (in bytes)
     allocated by ZBI when it is running."
    ::= { zbrZbiStartInfo 2 }

zbrZbiStartInfoExecute OBJECT-TYPE
    SYNTAX  INTEGER {
        no(1),
        yes(2)
    }
    MAX-ACCESS  read-write
    STATUS  current
    DESCRIPTION
    " Execute ZBI the first time. This will run the file
    specified by zbrZbiStartInfoFileName OID if a valid file name is set.
    This will return 1 when it is read."
    ::= { zbrZbiStartInfo 3 }

--====================================================================================
-- zebra.zbrZbi.zbrZbiControl
--====================================================================================

zbrZbiCtrlTerminate OBJECT-TYPE
    SYNTAX  INTEGER {
        no(1),
        yes(2)
    }
    MAX-ACCESS  read-write
    STATUS  current
    DESCRIPTION
    " Terminate ZBI. This will return 1 when it is read."
    ::= { zbrZbiControl 1 }

zbrZbiCtrlRun OBJECT-TYPE
    SYNTAX  INTEGER {
        no(1),
        yes(2)
    }
    MAX-ACCESS  read-write
    STATUS  current
    DESCRIPTION
    " Run the currently loaded ZBI program from the
     beginning of the program. This will return 1 when it is read."
    ::= { zbrZbiControl 2 }

zbrZbiCtrlBreak OBJECT-TYPE
    SYNTAX  INTEGER {
        no(1),
        yes(2)
    }
    MAX-ACCESS  read-write
    STATUS  current
    DESCRIPTION
    " Stop the execution of the currently running ZBI program.
     The zbrZbiCtrlLineNumber OID specifies which line number the program will
     execute next if it is resumed. This will return 1 when it is read."
    ::= { zbrZbiControl 3 }

zbrZbiCtrlRestart OBJECT-TYPE
    SYNTAX  INTEGER {
        no(1),
        yes(2)
    }
    MAX-ACCESS  read-write
    STATUS  current
    DESCRIPTION
    " Resume the currently stopped ZBI program. The
     program will resume at the line specified by the zbrZbiCtrlLineNumber
     OID. This will return 1 when it is read."
    ::= { zbrZbiControl 4 }

zbrZbiCtrlStep OBJECT-TYPE
    SYNTAX  INTEGER {
        no(1),
        yes(2)
    }
    MAX-ACCESS  read-write
    STATUS  current
    DESCRIPTION
    " Execute the line specified by the zbrZbiCtrlLineNumber
     OID and adjust the program counter to the next line. The
     zbrZbiCtrlLineNumber OID will be updated to the next line to
     be executed in the program. This will return 1 when it is read."
    ::= { zbrZbiControl 5 }

zbrZbiCtrlVariableName OBJECT-TYPE
    SYNTAX  DisplayString
    MAX-ACCESS  read-write
    STATUS  current
    DESCRIPTION
    " Set the variable name you would like to read
     or modify the value of. Use the zbrZbiCtrlVariableValue OID to read
     or modify the value."
    ::= { zbrZbiControl 6 }

zbrZbiCtrlVariableValue OBJECT-TYPE
    SYNTAX  DisplayString
    MAX-ACCESS  read-write
    STATUS  current
    DESCRIPTION
    " Gets, or sets, the variable value using
     the last name supplied from the zbrZbiCtrlVariableName OID."
    ::= { zbrZbiControl 7 }

zbrZbiCtrlVariableTable OBJECT-TYPE
    SYNTAX  SEQUENCE OF ZbrZbiCtrlVariableEntry
    MAX-ACCESS  not-accessible
    STATUS  current
    DESCRIPTION
    "ZBI Variable Table. Lists the current variables and their values."
    ::= { zbrZbiControl 8 }

zbrZbiCtrlVariableEntry OBJECT-TYPE
    SYNTAX  ZbrZbiCtrlVariableEntry
    MAX-ACCESS  not-accessible
    STATUS  current
    DESCRIPTION
    "A ZBI variable entry"
    INDEX   { zbrZbiVariableIndex }
    ::= { zbrZbiCtrlVariableTable 1 }

ZbrZbiCtrlVariableEntry ::=
    SEQUENCE {
        zbrZbiVariableNameItem
            DisplayString,
        zbrZbiVariableValueItem
            DisplayString,
        zbrZbiVariableIndex
            INTEGER
    }

zbrZbiVariableNameItem OBJECT-TYPE
    SYNTAX  DisplayString
    MAX-ACCESS  read-only
    STATUS  current
    DESCRIPTION
    "ZBI Variable Name."
    ::= { zbrZbiCtrlVariableEntry 1 }

zbrZbiVariableValueItem OBJECT-TYPE
    SYNTAX  DisplayString
    MAX-ACCESS  read-only
    STATUS  current
    DESCRIPTION
    "ZBI Variable Value."
    ::= { zbrZbiCtrlVariableEntry 2 }

zbrZbiVariableIndex OBJECT-TYPE
    SYNTAX  INTEGER (0..2147483647)
    MAX-ACCESS  not-accessible
    STATUS  current
    DESCRIPTION
    "Index into a table"
    ::= { zbrZbiCtrlVariableEntry 3 }

zbrZbiCtrlAddBreakpoint OBJECT-TYPE
    SYNTAX  INTEGER
    MAX-ACCESS  read-write
    STATUS  current
    DESCRIPTION
    " Add a breakpoint to the supplied line number."
    ::= { zbrZbiControl 9 }

zbrZbiCtrlDeleteBreakpoint OBJECT-TYPE
    SYNTAX  INTEGER
    MAX-ACCESS  read-write
    STATUS  current
    DESCRIPTION
    " Delete Breakpoint using the supplied line number."
    ::= { zbrZbiControl 10 }

zbrZbiCtrlClearAllBreakpoints OBJECT-TYPE
    SYNTAX  INTEGER {
        no(1),
        yes(2)
    }
    MAX-ACCESS  read-write
    STATUS  current
    DESCRIPTION
    " Clear all breakpoints. This will return 1 when it is read."
    ::= { zbrZbiControl 11 }

zbrZbiCtrlLineNumber OBJECT-TYPE
    SYNTAX  INTEGER
    MAX-ACCESS  read-write
    STATUS  current
    DESCRIPTION
    " Get or set the current line number of the program being executed"
    ::= { zbrZbiControl 12 }

zbrZbiCtrlDebugTrapLocation OBJECT-TYPE
    SYNTAX  IpAddress
    MAX-ACCESS  read-write
    STATUS  current
    DESCRIPTION
    "Ip address where ZBI debug traps are sent by default.
     Not persistent. If not set, it defaults to 0.0.0.0 which ZBI re-interprets
     as 255.255.255.255(local broadcast)"
    ::= { zbrZbiControl 13 }

--====================================================================================
-- zebra.zbrUsbHost
--====================================================================================

zbrUsbHostMassStorageCount OBJECT-TYPE
    SYNTAX INTEGER
    MAX-ACCESS read-only
    STATUS current
    DESCRIPTION
    " The number of mass storage devices connected to the USB Host port"
    ::= { zbrUsbHost 1 }

zbrUsbHostHidCount OBJECT-TYPE
    SYNTAX INTEGER
    MAX-ACCESS read-only
    STATUS current
    DESCRIPTION
    " The number of HID devices connected to the USB Host port"
    ::= { zbrUsbHost 2 }

zbrUsbHostReadList OBJECT-TYPE
    SYNTAX DisplayString (SIZE (0..20))
    MAX-ACCESS read-write
    STATUS current
    DESCRIPTION
    "Print or store files from the usb drive"
    ::= { zbrUsbHost 3 }

zbrUsbHostReadListPrintDelay OBJECT-TYPE
    SYNTAX INTEGER
    MAX-ACCESS read-write
    STATUS current
    DESCRIPTION
    " The number of milliseconds to delay after printing each file after using SELECT ALL"
    ::= { zbrUsbHost 4 }

zbrUsbHostLockOut OBJECT-TYPE
    SYNTAX INTEGER {
        on(1),
        off(2)
    }
    MAX-ACCESS read-write
    STATUS current
    DESCRIPTION
    "on/off disables/enables USB HOST respectively"
    ::= { zbrUsbHost 5 }

zbrUsbHostWriteList OBJECT-TYPE
    SYNTAX DisplayString (SIZE (0..20))
    MAX-ACCESS read-write
    STATUS current
    DESCRIPTION
    "Store files from the flash drive to USB drive"
    ::= { zbrUsbHost 6 }
 
zbrUsbHostTemplateList OBJECT-TYPE
    SYNTAX DisplayString (SIZE (0..20))
    MAX-ACCESS read-write
    STATUS current
    DESCRIPTION
    "List *.ZPL files from the E drive"
    ::= { zbrUsbHost 8 } 
    
zbrUsbHostTemplatePrintAmount OBJECT-TYPE
    SYNTAX DisplayString (SIZE (0..20))
    MAX-ACCESS read-write
    STATUS current
    DESCRIPTION
    "The number of template labels to printed"
    ::= { zbrUsbHost 9 } 
       
zbrUsbHostFnFieldList OBJECT-TYPE
    SYNTAX DisplayString (SIZE (0..20))
    MAX-ACCESS read-write
    STATUS current
    DESCRIPTION
    "Control .zpl template file fn Prompts and Answers"
    ::= { zbrUsbHost 10 } 
       
zbrUsbHostFnLastField OBJECT-TYPE
    SYNTAX INTEGER {
        yes(1),
        no(2)
    }
    MAX-ACCESS read-only
    STATUS current
    DESCRIPTION
    "Returns yes or no if the currently selected FN Prompt is the last on in the .zpl template file"
    ::= { zbrUsbHost 11 } 
       
zbrUsbHostFnFieldData OBJECT-TYPE
    SYNTAX DisplayString (SIZE (0..20))
    MAX-ACCESS read-write
    STATUS current
    DESCRIPTION
    "Used to get/set the Answer to a .zpl template file Prompt"
    ::= { zbrUsbHost 12 } 
    
zbrUsbHostKeyboardInput OBJECT-TYPE
    SYNTAX INTEGER {
        on(1),
        off(2)
    }
    MAX-ACCESS read-write
    STATUS current
    DESCRIPTION
    "on/off disables/enables USB keyboard input"
    ::= { zbrUsbHost 13 }
    
zbrUsbHostConfigInfoToUsb OBJECT-TYPE
   SYNTAX INTEGER {
        no(1),
        yes(2)
    }
   MAX-ACCESS read-write
   STATUS current
   DESCRIPTION
    " Save the printer configuration info to usb thumb drive."
   ::= { zbrUsbHost 14 }
       
--====================================================================================
-- zebra.zbrUsbMirror
--====================================================================================

zbrUsbMirrorEnable OBJECT-TYPE
    SYNTAX INTEGER {
        on(1),
        off(2)
    }
    MAX-ACCESS read-write
    STATUS current
    DESCRIPTION
    "on/off enables/disables USB Mirror"
    ::= { zbrUsbMirror 1 }

zbrUsbMirrorAuto OBJECT-TYPE
    SYNTAX INTEGER {
        on(1),
        off(2),
        prompt(3)
    }
    MAX-ACCESS  read-write
    STATUS  current
    DESCRIPTION
    "automatically run mirror or force a prompt to run mirror"
    ::= { zbrUsbMirror 2 }

zbrUsbMirrorErrorRetry OBJECT-TYPE
   SYNTAX INTEGER (0..65535)
   MAX-ACCESS read-write
   STATUS current
   DESCRIPTION
   "Error retry time in minutes."
   ::= { zbrUsbMirror 3 }

zbrUsbMirrorFetch OBJECT-TYPE
   SYNTAX INTEGER {
        fetch(1)
    }
   MAX-ACCESS read-write
   STATUS current
   DESCRIPTION
   "Force the usb mirror process to be run immediately."
   ::= { zbrUsbMirror 4 }

zbrUsbMirrorLastError OBJECT-TYPE
   SYNTAX DisplayString (SIZE (0..255))
   MAX-ACCESS read-only
   STATUS current
   DESCRIPTION
   "Last mirror error run over usb."
   ::= { zbrUsbMirror 5 }

zbrUsbMirrorLastTime OBJECT-TYPE
   SYNTAX DisplayString (SIZE (0..100))
   MAX-ACCESS read-only
   STATUS current
   DESCRIPTION
   "Time of the last attempted usb mirror fetch, accurate to the second."
   ::= { zbrUsbMirror 6 }

zbrUsbMirrorPath OBJECT-TYPE
   SYNTAX DisplayString (SIZE (0..255))
   MAX-ACCESS read-write
   STATUS current
   DESCRIPTION
   "Path on the USB device where the mirror directory is located."
   ::= { zbrUsbMirror 7 }

zbrUsbMirrorResetDelay OBJECT-TYPE
    SYNTAX INTEGER (0..900)
    MAX-ACCESS read-write
    STATUS current
    DESCRIPTION
    "USB Mirror Reset Delay"
    ::= { zbrUsbMirror 8 }

zbrUsbMirrorSuccess OBJECT-TYPE
   SYNTAX INTEGER {
        yes(1),
        no(2)
    }
   MAX-ACCESS read-only
   STATUS current
   DESCRIPTION
   "Success or failure of the last usb mirror fetch."
   ::= { zbrUsbMirror 9 }

zbrUsbMirrorSuccessTime OBJECT-TYPE
   SYNTAX DisplayString (SIZE (0..100))
   MAX-ACCESS read-only
   STATUS current
   DESCRIPTION
   "Time of the last successful usb mirror fetch, accurate to the second."
   ::= { zbrUsbMirror 10 }

zbrUsbMirrorApplPath OBJECT-TYPE
   SYNTAX DisplayString (SIZE (0..255))
   MAX-ACCESS read-write
   STATUS current
   DESCRIPTION
   "Complete Explicit Path on the usb device where the mirror directory is located."
   ::= { zbrUsbMirror 11 }

--====================================================================================
-- zebra.zbrUsbOtg
--====================================================================================

zbrUsbOtgEnable OBJECT-TYPE
   SYNTAX INTEGER {
        off(1),
        device(2),
        host(3),
        otg(4)
   }
   MAX-ACCESS read-write
   STATUS current
   DESCRIPTION
   "SGD for setting the usb otg mode"
   ::= { zbrUsbOtg 1 }

zbrUsbOtgStatus OBJECT-TYPE
   SYNTAX INTEGER {
        disconnected(1),
        device(2),
        host(3)
   }
   MAX-ACCESS read-only
   STATUS current
    DESCRIPTION
    "SGD for reading the otg port status"
    ::= { zbrUsbOtg 2 }

--====================================================================================
-- zebra.zbrUsbMirror.zbrUsbMirrorFeedback
--====================================================================================

zbrUsbMirrorFeedbackAuto OBJECT-TYPE
   SYNTAX INTEGER {
        on(1),
        off(2)
    }
   MAX-ACCESS read-write
   STATUS current
   DESCRIPTION
   "If on, a feedback file is written from the printer to the usb device after each fetch. "
   ::= { zbrUsbMirrorFeedback 1 }

zbrUsbMirrorFeedbackPath OBJECT-TYPE
   SYNTAX DisplayString (SIZE (0..255))
   MAX-ACCESS read-write
   STATUS current
   DESCRIPTION
   "Path on the usb device where the feedback file will be written."
   ::= { zbrUsbMirrorFeedback 2 }

zbrUsbMirrorFeedbackOdometer OBJECT-TYPE
    SYNTAX Unsigned32
    MAX-ACCESS read-write
    STATUS current
    DESCRIPTION
    "USB Mirror Feedback Odometer"
    ::= { zbrUsbMirrorFeedback 3 }

--====================================================================================
-- zebra.zbrApl
--====================================================================================

zbrAplEnable OBJECT-TYPE
    SYNTAX  DisplayString (SIZE (0..20))
    MAX-ACCESS  read-write
    STATUS  current
    DESCRIPTION
    " Enable/disable virtual device"
    ::= { zbrApl 1 }

zbrAplFrameworkVersion OBJECT-TYPE
    SYNTAX  DisplayString (SIZE (0..20))
    MAX-ACCESS  read-only
    STATUS  current
    DESCRIPTION
    " Version of firmware framework"
    ::= { zbrApl 2 }
    
zbrAplVersion OBJECT-TYPE
    SYNTAX  DisplayString (SIZE (0..20))
    MAX-ACCESS  read-only
    STATUS  current
    DESCRIPTION
    " Version of running Virtual Device"
    ::= { zbrApl 3 }

zbrAplSettings OBJECT-TYPE
   SYNTAX  OCTET STRING (SIZE (0..256))
   MAX-ACCESS  read-write
   STATUS  current
   DESCRIPTION
   " Virtual device specific settings"
   ::= { zbrApl 4 }

zbrAplICropToLength OBJECT-TYPE
   SYNTAX INTEGER {
        on(1),
        off(2)
    }
    MAX-ACCESS  read-write
    STATUS  current
    DESCRIPTION
    "Enable/disable APL-I crop to length"
    ::= { zbrAplI 1 }

zbrAplDLegacyMode OBJECT-TYPE
   SYNTAX INTEGER {
       on(1),
       off(2)
    }
    MAX-ACCESS read-write
    STATUS current
    DESCRIPTION
    "SGD to set the APL-D legacy mode to [on,off]"
    ::= { zbrAplD 1 }

zbrAplInstalledVersions OBJECT-TYPE
    SYNTAX  OCTET STRING (SIZE (0..999))
    MAX-ACCESS  read-only
    STATUS  current
    DESCRIPTION
    "Name and version of each virtual device installed on the printer."
    ::= { zbrApl 6 }

--====================================================================================
-- zebra.zbrRibbon
--====================================================================================
zbrRibbonCartridgeAuthenticated OBJECT-TYPE
    SYNTAX INTEGER {
        yes(1),
        no(2),
        not-installed(3)
    }
   MAX-ACCESS read-only
   STATUS current
   DESCRIPTION
   "The status of the ribbon cartridge authentication."
   ::= { zbrCartridge 1 }
   
zbrRibbonCartridgeInserted OBJECT-TYPE
    SYNTAX INTEGER {
        yes(1),
        no(2)
    }
   MAX-ACCESS read-only
   STATUS current
   DESCRIPTION
   "Indicates whether a ribbon cartridge is inserted or not."
   ::= { zbrCartridge 2 }
   
zbrRibbonCartridgePartNumber OBJECT-TYPE
   SYNTAX DisplayString (SIZE (0..12))
   MAX-ACCESS read-only
   STATUS current
   DESCRIPTION
   "Ribbon Cartridge Part Number."
   ::= { zbrCartridge 3 }
   
zbrRibbonCartridgeSerialNumber OBJECT-TYPE
   SYNTAX DisplayString (SIZE (0..18))
   MAX-ACCESS read-only
   STATUS current
   DESCRIPTION
   "Ribbon Cartridge Serial Number."
   ::= { zbrCartridge 4 }
   
zbrRibbonCartridgeType OBJECT-TYPE
   SYNTAX DisplayString (SIZE (0..15))
   MAX-ACCESS read-only
   STATUS current
   DESCRIPTION
   "Type of Ribbon (wax/resin) in Cartridge."
   ::= { zbrCartridge 5 }

zbrRibbonCartridgeWidth OBJECT-TYPE
   SYNTAX INTEGER
   MAX-ACCESS read-only
   STATUS current
   DESCRIPTION
   "The Ribbon Width (in millimeters)."
   ::= { zbrCartridge 6 }
   
zbrRibbonCartridgeLength OBJECT-TYPE
   SYNTAX INTEGER
   MAX-ACCESS read-only
   STATUS current
   DESCRIPTION
   "The total ribbon cartridge capacity (length in meters)."
   ::= { zbrCartridge 7 }

zbrRibbonCartridgeLengthRemaining OBJECT-TYPE
   SYNTAX INTEGER
   MAX-ACCESS read-only
   STATUS current
   DESCRIPTION
   "The length of the ribbon (in meters) remaining in the cartridge."
   ::= { zbrCartridge 8 }

zbrRibbonCoating OBJECT-TYPE
   SYNTAX INTEGER {
      ink-side-out(1),
      ink-side-in(2)
   }
   MAX-ACCESS read-write
   STATUS current
   DESCRIPTION
   "The type of ribbon coating."
   ::= { zbrRibbon 2 }

zbrRibbonTension OBJECT-TYPE
   SYNTAX INTEGER {
      low(1),
      medium(2),
      high(3)
   }
   MAX-ACCESS read-write
   STATUS current
   DESCRIPTION
   "Tension of the ribbon."
   ::= { zbrRibbon 3 }

--====================================================================================
-- zebra.zbrSupplies
--====================================================================================
zbrSuppliesMediaPartNumber OBJECT-TYPE
   SYNTAX DisplayString (SIZE (0..64))
   MAX-ACCESS read-write
   STATUS current
   DESCRIPTION
   "User settable media part number."
   ::= { zbrSuppliesMedia 1 }
   
zbrSuppliesMediaSerialNumber OBJECT-TYPE
   SYNTAX DisplayString (SIZE (0..64))
   MAX-ACCESS read-write
   STATUS current
   DESCRIPTION
   "User settable media serial number."
   ::= { zbrSuppliesMedia 2 }
   
zbrSuppliesRibbonPartNumber OBJECT-TYPE
   SYNTAX DisplayString (SIZE (0..64))
   MAX-ACCESS read-write
   STATUS current
   DESCRIPTION
   "User settable ribbon part number."
   ::= { zbrSuppliesRibbon 1 }
   
zbrSuppliesRibbonSerialNumber OBJECT-TYPE
   SYNTAX DisplayString (SIZE (0..64))
   MAX-ACCESS read-write
   STATUS current
   DESCRIPTION
   "User settable ribbon serial number."
   ::= { zbrSuppliesRibbon 2 }
   
--====================================================================================
-- zebra.zbrSupplies.zbrSuppliesMediaCartTable
--====================================================================================
zbrSuppliesMediaCartTable OBJECT-TYPE
   SYNTAX  SEQUENCE OF ZbrSuppliesMediaCartTableEntry
   MAX-ACCESS  not-accessible
   STATUS  current
   DESCRIPTION "Supplies Media Cartridge Table."
   ::= { zbrSuppliesMedia 3 }

zbrSuppliesMediaCartTableEntry OBJECT-TYPE
   SYNTAX  ZbrSuppliesMediaCartTableEntry
   MAX-ACCESS  not-accessible
   STATUS  current
   DESCRIPTION "Supplies Media Cartridge Table entry."
   INDEX { zbrSuppliesMediaCartIndex }
   ::= { zbrSuppliesMediaCartTable 1 }

ZbrSuppliesMediaCartTableEntry ::= SEQUENCE {
      zbrSuppliesMediaCartIndex           INTEGER,
      zbrSuppliesMediaCartCounter         INTEGER,
      zbrSuppliesMediaCartPart            DisplayString,
      zbrSuppliesMediaCartSerial          DisplayString,
      zbrSuppliesMediaCartLength          INTEGER,
      zbrSuppliesMediaCartWidth           INTEGER,
      zbrSuppliesMediaCartSpeed           INTEGER,
      zbrSuppliesMediaCartDarkness        INTEGER,
      zbrSuppliesMediaCartTotalLabelCount INTEGER,
      zbrSuppliesMediaCartLabelsInitial   INTEGER,
      zbrSuppliesMediaCartLabelsRemain    INTEGER
   }

zbrSuppliesMediaCartIndex OBJECT-TYPE
   SYNTAX INTEGER (0..100)
   MAX-ACCESS read-only
   STATUS current
   DESCRIPTION "The index of cartridge data table entries (0-100)."
   ::= { zbrSuppliesMediaCartTableEntry 1 }

zbrSuppliesMediaCartCounter OBJECT-TYPE
   SYNTAX INTEGER
   MAX-ACCESS read-only
   STATUS current
   DESCRIPTION  "The counter of cartridge insertion entry."
   ::= { zbrSuppliesMediaCartTableEntry 2 }

zbrSuppliesMediaCartPart OBJECT-TYPE
   SYNTAX DisplayString
   MAX-ACCESS read-only
   STATUS current
   DESCRIPTION "The part number of the media cartridge."
   ::= { zbrSuppliesMediaCartTableEntry 3 }

zbrSuppliesMediaCartSerial OBJECT-TYPE
   SYNTAX DisplayString
   MAX-ACCESS read-only
   STATUS current
   DESCRIPTION "The serial number of the cartridge."
   ::= { zbrSuppliesMediaCartTableEntry 4 }

zbrSuppliesMediaCartLength OBJECT-TYPE
   SYNTAX INTEGER
   MAX-ACCESS read-only
   STATUS current
   DESCRIPTION "The total length of the media in the cartridge."
   ::= { zbrSuppliesMediaCartTableEntry 5 }

zbrSuppliesMediaCartWidth OBJECT-TYPE
   SYNTAX INTEGER
   MAX-ACCESS read-only
   STATUS current
   DESCRIPTION "The width of the media in the cartridge."
   ::= { zbrSuppliesMediaCartTableEntry 6 }

zbrSuppliesMediaCartSpeed OBJECT-TYPE
   SYNTAX INTEGER
   MAX-ACCESS read-only
   STATUS current
   DESCRIPTION "The print speed to be used with the cartridge."
   ::= { zbrSuppliesMediaCartTableEntry 7 }

zbrSuppliesMediaCartDarkness OBJECT-TYPE
   SYNTAX INTEGER
   MAX-ACCESS read-only
   STATUS current
   DESCRIPTION "The print darkness to be used with the cartridge."
   ::= { zbrSuppliesMediaCartTableEntry 8 }

zbrSuppliesMediaCartTotalLabelCount OBJECT-TYPE
   SYNTAX INTEGER
   MAX-ACCESS read-only
   STATUS current
   DESCRIPTION "The total number of labels in a new cartridge."
   ::= { zbrSuppliesMediaCartTableEntry 9 }

zbrSuppliesMediaCartLabelsInitial OBJECT-TYPE
   SYNTAX INTEGER
   MAX-ACCESS read-only
   STATUS current
   DESCRIPTION "The total number of labels in the cartridge at the moment inserted to the printer."
   ::= { zbrSuppliesMediaCartTableEntry 10 }

zbrSuppliesMediaCartLabelsRemain OBJECT-TYPE
   SYNTAX INTEGER
   MAX-ACCESS read-only
   STATUS current
   DESCRIPTION "The total number of labels remaining in the cartridge at the moment it was removed from the printer."
   ::= { zbrSuppliesMediaCartTableEntry 11 }

--====================================================================================
-- zebra.zbrSupplies.zbrSuppliesRibbonCartTable
--====================================================================================
zbrSuppliesRibbonCartTable OBJECT-TYPE
   SYNTAX  SEQUENCE OF ZbrSuppliesRibbonCartTableEntry
   MAX-ACCESS  not-accessible
   STATUS  current
   DESCRIPTION "Ribbon Used Table."
   ::= { zbrSuppliesRibbon 3 }

zbrSuppliesRibbonCartTableEntry OBJECT-TYPE
   SYNTAX  ZbrSuppliesRibbonCartTableEntry
   MAX-ACCESS  not-accessible
   STATUS  current
   DESCRIPTION "Supplies Ribbon Cartridge Table entry."
   INDEX { zbrSuppliesRibbonCartIndex }
   ::= { zbrSuppliesRibbonCartTable 1 }

ZbrSuppliesRibbonCartTableEntry ::= SEQUENCE {
      zbrSuppliesRibbonCartIndex    INTEGER,
      zbrSuppliesRibbonCartCounter  INTEGER,
      zbrSuppliesRibbonCartPart     DisplayString,
      zbrSuppliesRibbonCartSerial   DisplayString,
      zbrSuppliesRibbonCartType     INTEGER,
      zbrSuppliesRibbonCartLength   INTEGER,
      zbrSuppliesRibbonCartWidth    INTEGER,
      zbrSuppliesRibbonCartInitial  INTEGER,
      zbrSuppliesRibbonCartRemain   INTEGER
   }

zbrSuppliesRibbonCartIndex OBJECT-TYPE
   SYNTAX INTEGER (0..100)
   MAX-ACCESS read-only
   STATUS current
   DESCRIPTION "The index of cartridge data table entries (0-100)."
   ::= { zbrSuppliesRibbonCartTableEntry 1 }

zbrSuppliesRibbonCartCounter OBJECT-TYPE
   SYNTAX INTEGER
   MAX-ACCESS read-only
   STATUS current
   DESCRIPTION  "The counter of cartridge insertion entry."
   ::= { zbrSuppliesRibbonCartTableEntry 2 }

zbrSuppliesRibbonCartPart OBJECT-TYPE
   SYNTAX DisplayString
   MAX-ACCESS read-only
   STATUS current
   DESCRIPTION "The part number of the ribbon cartridge."
   ::= { zbrSuppliesRibbonCartTableEntry 3 }

zbrSuppliesRibbonCartSerial OBJECT-TYPE
   SYNTAX DisplayString
   MAX-ACCESS read-only
   STATUS current
   DESCRIPTION "The serial number of the cartridge."
   ::= { zbrSuppliesRibbonCartTableEntry 4 }

zbrSuppliesRibbonCartType OBJECT-TYPE
   SYNTAX INTEGER {
      wax(1),
      resin(2),
      wax-resin(3)
   }
   MAX-ACCESS read-only
   STATUS current
   DESCRIPTION "The chemical composition of the ribbon in the cartridge. 
         Possible responses are 'wax', 'resin', 'wax-resin'."
   ::= { zbrSuppliesRibbonCartTableEntry 5 }

zbrSuppliesRibbonCartLength OBJECT-TYPE
   SYNTAX INTEGER
   MAX-ACCESS read-only
   STATUS current
   DESCRIPTION "The total length of the ribbon in the cartridge."
   ::= { zbrSuppliesRibbonCartTableEntry 6 }

zbrSuppliesRibbonCartWidth OBJECT-TYPE
   SYNTAX INTEGER
   MAX-ACCESS read-only
   STATUS current
   DESCRIPTION "The width of the ribbon in the cartridge."
   ::= {zbrSuppliesRibbonCartTableEntry 7 }

zbrSuppliesRibbonCartInitial OBJECT-TYPE
   SYNTAX INTEGER
   MAX-ACCESS read-only
   STATUS current
   DESCRIPTION "The total length of ribbon in the cartridge at the moment inserted to the printer."
   ::= { zbrSuppliesRibbonCartTableEntry 8 }

zbrSuppliesRibbonCartRemain OBJECT-TYPE
   SYNTAX INTEGER
   MAX-ACCESS read-only
   STATUS current
   DESCRIPTION "The total length of ribbon remaining in the cartridge at the moment it was removed from the printer."
   ::= { zbrSuppliesRibbonCartTableEntry 9 }

--====================================================================================
-- zebra.zbrSuppliesMedia.zbrSuppliesMediaRollTable
--====================================================================================
zbrSuppliesMediaRollTable OBJECT-TYPE
   SYNTAX  SEQUENCE OF ZbrSuppliesMediaRollTableEntry
   MAX-ACCESS  not-accessible
   STATUS  current
   DESCRIPTION "Supplies Media Roll Table."
   ::= { zbrSuppliesMedia 4 }

zbrSuppliesMediaRollTableEntry OBJECT-TYPE
   SYNTAX  ZbrSuppliesMediaRollTableEntry
   MAX-ACCESS  not-accessible
   STATUS  current
   DESCRIPTION "Supplies Media Roll Table entry."
   INDEX { zbrSuppliesMediaRollIndex }
   ::= { zbrSuppliesMediaRollTable 1 }

ZbrSuppliesMediaRollTableEntry ::= SEQUENCE {
      zbrSuppliesMediaRollIndex            INTEGER,
      zbrSuppliesMediaRollLoaded           INTEGER,
      zbrSuppliesMediaRollPart             DisplayString,
      zbrSuppliesMediaRollSerial           DisplayString,
      zbrSuppliesMediaRollLength           INTEGER,
      zbrSuppliesMediaRollWidth            INTEGER,
      zbrSuppliesMediaRollSpeed            INTEGER,
      zbrSuppliesMediaRollDarkness         INTEGER,
      zbrSuppliesMediaRollTotalLabelCount  INTEGER,
      zbrSuppliesMediaRollLabelsRemain     INTEGER
   }

zbrSuppliesMediaRollIndex OBJECT-TYPE
   SYNTAX INTEGER (0..30)
   MAX-ACCESS read-only
   STATUS current
   DESCRIPTION "The index of the last 30 calibrated label lengths (0-30)."
   ::= { zbrSuppliesMediaRollTableEntry 1 }

zbrSuppliesMediaRollLoaded OBJECT-TYPE
   SYNTAX INTEGER {
      yes(1),
      no(2)
   }
   MAX-ACCESS read-only
   STATUS current
   DESCRIPTION "Is a media loaded, yes or no."
   ::= { zbrSuppliesMediaRollTableEntry 2 }

zbrSuppliesMediaRollPart OBJECT-TYPE
   SYNTAX DisplayString
   MAX-ACCESS read-only
   STATUS current
   DESCRIPTION "The part number of the media currently loaded."
   ::= { zbrSuppliesMediaRollTableEntry 3 }

zbrSuppliesMediaRollSerial OBJECT-TYPE
   SYNTAX DisplayString
   MAX-ACCESS read-only
   STATUS current
   DESCRIPTION "The serial number of the media roll currently loaded."
   ::= { zbrSuppliesMediaRollTableEntry 4 }

zbrSuppliesMediaRollLength OBJECT-TYPE
   SYNTAX INTEGER
   MAX-ACCESS read-only
   STATUS current
   DESCRIPTION "The calibrated length of the currently loaded media."
   ::= { zbrSuppliesMediaRollTableEntry 5 }

zbrSuppliesMediaRollWidth OBJECT-TYPE
   SYNTAX INTEGER
   MAX-ACCESS read-only
   STATUS current
   DESCRIPTION "The width of the currently loaded media."
   ::= { zbrSuppliesMediaRollTableEntry 6 }

zbrSuppliesMediaRollSpeed OBJECT-TYPE
   SYNTAX INTEGER
   MAX-ACCESS read-only
   STATUS current
   DESCRIPTION "The print speed to be used with the currently loaded media."
   ::= { zbrSuppliesMediaRollTableEntry 7 }

zbrSuppliesMediaRollDarkness OBJECT-TYPE
   SYNTAX INTEGER
   MAX-ACCESS read-only
   STATUS current
   DESCRIPTION "The print darkness to be used with the currently loaded media."
   ::= { zbrSuppliesMediaRollTableEntry 8 }

zbrSuppliesMediaRollTotalLabelCount OBJECT-TYPE
   SYNTAX INTEGER
   MAX-ACCESS read-only
   STATUS current
   DESCRIPTION "The total number of labels in a new media roll."
   ::= { zbrSuppliesMediaRollTableEntry 9 }

zbrSuppliesMediaRollLabelsRemain OBJECT-TYPE
   SYNTAX INTEGER
   MAX-ACCESS read-only
   STATUS current
   DESCRIPTION "The total number of labels remaining in the currently loaded media. To be updated at each print event."
   ::= { zbrSuppliesMediaRollTableEntry 10 }


--=================================================================================================
--zebra.zbrLinkOsConnector
--=================================================================================================
zbrLinkOsConnectorVersion OBJECT-TYPE
   SYNTAX DisplayString (SIZE (0..6))
   MAX-ACCESS read-only
   STATUS current
   DESCRIPTION
   "Version of LinkOS Connect feature."
   ::= { zbrLinkOsConnector 1 }
 
zbrLinkOsConnectorConnect OBJECT-TYPE
   SYNTAX  INTEGER {
      on(1),
      off(2)
   }
   MAX-ACCESS read-write
   STATUS current
   DESCRIPTION
   "State of LinkOS Connect feature."
   ::= { zbrLinkOsConnector 2 }

zbrLinkOsConnectorProxy OBJECT-TYPE
    SYNTAX  OCTET STRING (SIZE (0..2048))
    MAX-ACCESS read-write
    STATUS current
    DESCRIPTION
    " Assigns the URL of the proxy for this connection."
    ::= { zbrLinkOsConnector 3 }

zbrLinkOsConnectorAuthenticationAdd OBJECT-TYPE
    SYNTAX  OCTET STRING (SIZE (0..2048))
    MAX-ACCESS read-write
    STATUS current
    DESCRIPTION
    " Allows the user to add a single server/username/password
     triplet into the list of authentication entries. There may be multiple
     authentication requests along the route to the destination. For each HTTP authentication
     request received while attempting to connect, the printer will enumerate the authentication
     entries and attempt to satisfy the request with the username/password pair provided for
     the respective server. The server name in the entry is what determines which username/password
     pair should be used for which authentication request. Both dns names and IP addresses
     are acceptable. The server, username, and password are separated by a single space (not a
     tab or other white space character). The server name is the only required field. If no
     username is supplied, but a password is, there must be two spaces between the server and
     the password fields. If there is a username but no password, or simply just the
     servername, no space is required at the end of the entry."
    ::= { zbrLinkOsConnector 4 }

zbrLinkOsConnectorAuthenticationRemove OBJECT-TYPE
    SYNTAX  OCTET STRING (SIZE (0..2048))
    MAX-ACCESS read-write
    STATUS current
    DESCRIPTION
    " Allows the user to remove a single
     server/username/password triplet from the list of authentication entries. To
     remove an entry only the server name is supplied however the entire entry will be
     removed. If an invalid entry is supplied no action is taken."
    ::= { zbrLinkOsConnector 5 }

zbrLinkOsConnectorAuthenticationEntries OBJECT-TYPE
    SYNTAX  DisplayString
    MAX-ACCESS read-only
    STATUS current
    DESCRIPTION
    " Lists the server names added to the authentication
     entries list. Only the server names will be shown. The username and passwords will not be shown."
    ::= { zbrLinkOsConnector 6 }    

--====================================================================================
-- zebra.zbrMedia
--====================================================================================
zbrMediaCartridgeInserted OBJECT-TYPE
    SYNTAX INTEGER {
        yes(1),
        no(2)
    }
   MAX-ACCESS read-only
   STATUS current
   DESCRIPTION
   "Indicates whether a media cartridge is inserted."
   ::= { zbrMediaCartridge 1 }
   
zbrMediaCartridgePartNumber OBJECT-TYPE
   SYNTAX DisplayString (SIZE (0..12))
   MAX-ACCESS read-only
   STATUS current
   DESCRIPTION
   "Part Number of the media cartridge."
   ::= { zbrMediaCartridge 2 }
   
zbrMediaCartridgeSerialNumber OBJECT-TYPE
   SYNTAX DisplayString (SIZE (0..16))
   MAX-ACCESS read-only
   STATUS current
   DESCRIPTION
   "Serial Number of the media cartridge."
   ::= { zbrMediaCartridge 3 }
   
zbrMediaCartridgeLength OBJECT-TYPE
   SYNTAX INTEGER
   MAX-ACCESS read-only
   STATUS current
   DESCRIPTION
   "Label length in dots of the media cartridge."
   ::= { zbrMediaCartridge 4 }

zbrMediaCartridgeWidth OBJECT-TYPE
   SYNTAX INTEGER
   MAX-ACCESS read-only
   STATUS current
   DESCRIPTION
   "Label width in dots of the media cartridge."
   ::= { zbrMediaCartridge 5 }
   
zbrMediaCartridgeSpeed OBJECT-TYPE
   SYNTAX INTEGER
   MAX-ACCESS read-only
   STATUS current
   DESCRIPTION
   "The print speed for the media cartridge."
   ::= { zbrMediaCartridge 6 }
   
zbrMediaCartridgeDarkness OBJECT-TYPE
   SYNTAX INTEGER
   MAX-ACCESS read-only
   STATUS current
   DESCRIPTION
   "The optimal darkness for labels in the media cartridge."
   ::= { zbrMediaCartridge 7 }
   
zbrMediaCartridgeTotalLabelCount OBJECT-TYPE
   SYNTAX INTEGER
   MAX-ACCESS read-only
   STATUS current
   DESCRIPTION
   "Total label count of the media cartridge."
   ::= { zbrMediaCartridge 8 }

zbrMediaCartridgeLabelsRemaining OBJECT-TYPE
   SYNTAX INTEGER
   MAX-ACCESS read-only
   STATUS current
   DESCRIPTION
   "Indicates the number of labels remaining in the media cartridge."
   ::= { zbrMediaCartridge 9 }

zbrMediaBackfeedPercent OBJECT-TYPE
   SYNTAX INTEGER {
      normal(1),
      after(2),
      off(3),
      before(4),
      percent-10(5),
      percent-20(6),
      percent-30(7),
      percent-40(8),
      percent-50(9),
      percent-60(10),
      percent-70(11),
      percent-80(12)
   }
   MAX-ACCESS read-write
   STATUS current
   DESCRIPTION
   "The backfeed percent, equivalent to the ZPL ~JS command."
   
   ::= { zbrMedia 2 }
   
zbrMediaLinerlessOffset OBJECT-TYPE
   SYNTAX INTEGER
   MAX-ACCESS read-write
   STATUS current
   DESCRIPTION
   "Linerless media offset, no print zone or leader length configuration. The data range is based on the resolution of the printer."
   ::= { zbrMedia 3 }

--====================================================================================
-- zebra.zbrCutter
--====================================================================================
zbrCutterCleanReminderEnable OBJECT-TYPE
   SYNTAX INTEGER {
     enabled(1),
     disabled(2)
   }
   MAX-ACCESS read-write
   STATUS current
   DESCRIPTION
   "Cutter cleaning reminder feature configuration."
   ::= { zbrCutter 1 }
   
zbrCutterCleanReminderThreshold OBJECT-TYPE
   SYNTAX Unsigned32
   MAX-ACCESS read-write
   STATUS current
   DESCRIPTION
   "Threshold value to trigger cleaning reminder alert."
   ::= { zbrCutter 2 }

END
